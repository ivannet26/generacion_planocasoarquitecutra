;; ============================================================================
;; UBI_BUSQUEDA.lsp - Sistema GM Ingenieros (modulo ubi)
;; Movido SIN CAMBIOS desde PLANO_UBICACION.lsp (division PRY2 2026-10-13).
;; El orden de carga vive en lisp/MANIFIESTO_MODULOS.txt.
;; ============================================================================


;; --- FUNCION DE RECUPERACI\\U+00D3N DE MEMORIA DEL DWG ---
(defun UBI_RestoreDWGMemory ( / tmp_code ss_vp i e_vp v_num scale_idx cenpt vp_data existing)
  (setq tmp_code (vlax-ldata-get "ML_SUITE" "TARGET_CODE"))
  (if (and tmp_code (/= tmp_code "")) (setq *UBI_TARGET_CODE* tmp_code))
  
  (setq *UBI_VP_DICT* '())
  (setq ss_vp (ssget "X" '((0 . "VIEWPORT"))))
  (if ss_vp
    (progn
      (setq i 0)
      (while (< i (sslength ss_vp))
        (setq e_vp (ssname ss_vp i))
        (setq v_num (vlax-ldata-get e_vp "ML_VP_NUM"))
        (if v_num
          (progn
            (setq scale_idx (vlax-ldata-get e_vp "DYN_VP_SCALE_IDX"))
            (setq cenpt (vlax-ldata-get e_vp "DYN_VP_CENTER"))
            (setq vp_data (list e_vp cenpt scale_idx))
            (setq existing (assoc v_num *UBI_VP_DICT*))
            (if existing
              (setq *UBI_VP_DICT* (subst (cons v_num (list vp_data)) existing *UBI_VP_DICT*))
              (setq *UBI_VP_DICT* (append *UBI_VP_DICT* (list (cons v_num (list vp_data)))))
            )
          )
        )
        (setq i (1+ i))
      )
      (setq ss_vp nil) (gc)
    )
  )
)

;; =========================================================================================
;; --- TABLAS MAESTRAS DE DIMENSIONES ---
;; =========================================================================================
(setq *UBI_DATA_MAP_NORMAL* '( ;; BQ 2026-09-21: orden (esc texto dist estaca grillaInt grillaAlt gap prog diametro). Diametro Excel (nth 8) al final para no mover nth 1-7 de grilla.
  ("20" 0.04 0.036 0.08 2.0 0.04 0.02 0.04 0.02) ("25" 0.05 0.045 0.10 3.0 0.05 0.03 0.05 0.025) ("50" 0.10 0.090 0.20 5.0 0.10 0.05 0.10 0.05)
  ("75" 0.15 0.135 0.30 8.0 0.15 0.08 0.15 0.075) ("100" 0.20 0.180 0.40 10.0 0.20 0.10 0.20 0.10) ("125" 0.25 0.225 0.50 13.0 0.25 0.13 0.25 0.125)
  ("200" 0.40 0.360 0.80 20.0 0.40 0.20 0.40 0.20) ("250" 0.50 0.450 1.00 25.0 0.50 0.25 0.50 0.25) ("500" 1.00 0.900 2.00 50.0 1.00 0.50 1.00 0.50)
  ("750" 1.50 1.350 3.00 75.0 1.50 0.75 1.50 0.75) ("1000" 2.00 1.800 4.00 100.0 2.00 1.00 2.00 1.00) ("1250" 2.50 2.250 5.00 125.0 2.50 1.25 2.50 1.25)
  ("2000" 4.00 3.600 8.00 200.0 4.00 2.00 4.00 2.00) ("2500" 5.00 4.500 10.00 250.0 5.00 2.50 5.00 2.50) ("5000" 10.00 9.000 20.00 500.0 10.00 5.00 10.00 5.00)
  ("7500" 15.00 13.500 30.00 750.0 15.00 7.50 15.00 7.50) ("10000" 20.00 18.000 40.00 1000.0 20.00 10.00 20.00 10.00)
  ("12500" 25.00 22.500 50.00 1250.0 25.00 12.50 25.00 12.50) ("20000" 40.00 36.000 80.00 2000.0 40.00 20.00 40.00 20.00)
  ("25000" 50.00 45.000 100.00 2500.0 50.00 25.00 50.00 25.00)
))

(setq *UBI_DATA_MAP_UBICACION* '( ;; BQ 2026-09-21: valores literales Excel (dist redondeada a 3 dec). Diametro INFERIDO mitad NORMAL (Excel sin columna; igual que estacas): documentado en SPEC.
  ("20" 0.020 0.018 0.04 2.0 0.04 0.02 0.020 0.010) ("25" 0.025 0.023 0.05 3.0 0.05 0.03 0.025 0.0125) ("50" 0.050 0.045 0.10 5.0 0.10 0.05 0.050 0.025)
  ("75" 0.075 0.068 0.15 8.0 0.15 0.08 0.075 0.0375) ("100" 0.100 0.090 0.20 10.0 0.20 0.10 0.100 0.05) ("125" 0.125 0.113 0.25 13.0 0.25 0.13 0.125 0.0625)
  ("200" 0.200 0.180 0.40 20.0 0.40 0.20 0.200 0.10) ("250" 0.250 0.225 0.50 25.0 0.50 0.25 0.250 0.125) ("500" 0.500 0.450 1.00 50.0 1.00 0.50 0.500 0.25)
  ("750" 0.750 0.675 1.50 75.0 1.50 0.75 0.750 0.375) ("1000" 1.000 0.900 2.00 100.0 2.00 1.00 1.000 0.50) ("1250" 1.250 1.125 2.50 125.0 2.50 1.25 1.250 0.625)
  ("2000" 2.000 1.800 4.00 200.0 4.00 2.00 2.000 1.00) ("2500" 2.500 2.250 5.00 250.0 5.00 2.50 2.500 1.25) ("5000" 5.000 4.500 10.00 500.0 10.00 5.00 5.000 2.50)
  ("7500" 7.500 6.750 15.00 750.0 15.00 7.50 7.500 3.75) ("10000" 10.000 9.000 20.00 1000.0 20.00 10.00 10.000 5.00)
  ("12500" 12.500 11.250 25.00 1250.0 25.00 12.50 12.500 6.25) ("20000" 20.000 18.000 40.00 2000.0 40.00 20.00 20.000 10.00)
  ("25000" 25.000 22.500 50.00 2500.0 50.00 25.00 25.000 12.50)
))

(setq *UBI_STYLE_MAP* '( ;; BP 2026-09-21: tabla estricta ESCALAS.xlsx hoja UBICACION (20 escalas). lts/lw/color fijos por elemento; gw/hscale por escala. Sin cambios de logica.
  ("20" ("Derecho" (color . 230) (ltype . "Continuous") (lts . 0.2) (lw . 40) (gw . 0.010) (ltgen . nil)) ("Eje" (color . 24) (ltype . "DASHDOT") (lts . 0.2) (lw . 40) (gw . 0.005) (ltgen . T)) ("Predios" (color . 64) (ltype . "Continuous") (lts . 1.0) (lw . -3) (gw . 0.004) (ltgen . nil)) ("Afectada" (color . 1) (ltype . "DASHED2") (lts . 5.0) (lw . 50) (gw . 0.004) (ltgen . T)) ("Achurado" (color . 71) (pattern . "SOLID") (ltype . "Continuous") (lts . 1.0) (lw . 50) (hscale . 0.002)) ("Matriz" (color . 5) (ltype . "Continuous") (lts . 1.0) (lw . 50) (gw . 0.006) (ltgen . nil)) ("Rios" (color . 4) (ltype . "Continuous") (lts . 0.2) (lw . 40) (gw . 0.004) (ltgen . nil)))
  ("25" ("Derecho" (color . 230) (ltype . "Continuous") (lts . 0.2) (lw . 40) (gw . 0.013) (ltgen . nil)) ("Eje" (color . 24) (ltype . "DASHDOT") (lts . 0.2) (lw . 40) (gw . 0.006) (ltgen . T)) ("Predios" (color . 64) (ltype . "Continuous") (lts . 1.0) (lw . -3) (gw . 0.005) (ltgen . nil)) ("Afectada" (color . 1) (ltype . "DASHED2") (lts . 5.0) (lw . 50) (gw . 0.005) (ltgen . T)) ("Achurado" (color . 71) (pattern . "SOLID") (ltype . "Continuous") (lts . 1.0) (lw . 50) (hscale . 0.003)) ("Matriz" (color . 5) (ltype . "Continuous") (lts . 1.0) (lw . 50) (gw . 0.008) (ltgen . nil)) ("Rios" (color . 4) (ltype . "Continuous") (lts . 0.2) (lw . 40) (gw . 0.005) (ltgen . nil)))
  ("50" ("Derecho" (color . 230) (ltype . "Continuous") (lts . 0.2) (lw . 40) (gw . 0.025) (ltgen . nil)) ("Eje" (color . 24) (ltype . "DASHDOT") (lts . 0.2) (lw . 40) (gw . 0.013) (ltgen . T)) ("Predios" (color . 64) (ltype . "Continuous") (lts . 1.0) (lw . -3) (gw . 0.010) (ltgen . nil)) ("Afectada" (color . 1) (ltype . "DASHED2") (lts . 5.0) (lw . 50) (gw . 0.010) (ltgen . T)) ("Achurado" (color . 71) (pattern . "SOLID") (ltype . "Continuous") (lts . 1.0) (lw . 50) (hscale . 0.005)) ("Matriz" (color . 5) (ltype . "Continuous") (lts . 1.0) (lw . 50) (gw . 0.016) (ltgen . nil)) ("Rios" (color . 4) (ltype . "Continuous") (lts . 0.2) (lw . 40) (gw . 0.010) (ltgen . nil)))
  ("75" ("Derecho" (color . 230) (ltype . "Continuous") (lts . 0.2) (lw . 40) (gw . 0.038) (ltgen . nil)) ("Eje" (color . 24) (ltype . "DASHDOT") (lts . 0.2) (lw . 40) (gw . 0.019) (ltgen . T)) ("Predios" (color . 64) (ltype . "Continuous") (lts . 1.0) (lw . -3) (gw . 0.015) (ltgen . nil)) ("Afectada" (color . 1) (ltype . "DASHED2") (lts . 5.0) (lw . 50) (gw . 0.015) (ltgen . T)) ("Achurado" (color . 71) (pattern . "SOLID") (ltype . "Continuous") (lts . 1.0) (lw . 50) (hscale . 0.008)) ("Matriz" (color . 5) (ltype . "Continuous") (lts . 1.0) (lw . 50) (gw . 0.024) (ltgen . nil)) ("Rios" (color . 4) (ltype . "Continuous") (lts . 0.2) (lw . 40) (gw . 0.015) (ltgen . nil)))
  ("100" ("Derecho" (color . 230) (ltype . "Continuous") (lts . 0.2) (lw . 40) (gw . 0.050) (ltgen . nil)) ("Eje" (color . 24) (ltype . "DASHDOT") (lts . 0.2) (lw . 40) (gw . 0.025) (ltgen . T)) ("Predios" (color . 64) (ltype . "Continuous") (lts . 1.0) (lw . -3) (gw . 0.020) (ltgen . nil)) ("Afectada" (color . 1) (ltype . "DASHED2") (lts . 5.0) (lw . 50) (gw . 0.020) (ltgen . T)) ("Achurado" (color . 71) (pattern . "SOLID") (ltype . "Continuous") (lts . 1.0) (lw . 50) (hscale . 0.010)) ("Matriz" (color . 5) (ltype . "Continuous") (lts . 1.0) (lw . 50) (gw . 0.032) (ltgen . nil)) ("Rios" (color . 4) (ltype . "Continuous") (lts . 0.2) (lw . 40) (gw . 0.020) (ltgen . nil)))
  ("125" ("Derecho" (color . 230) (ltype . "Continuous") (lts . 0.2) (lw . 40) (gw . 0.063) (ltgen . nil)) ("Eje" (color . 24) (ltype . "DASHDOT") (lts . 0.2) (lw . 40) (gw . 0.031) (ltgen . T)) ("Predios" (color . 64) (ltype . "Continuous") (lts . 1.0) (lw . -3) (gw . 0.025) (ltgen . nil)) ("Afectada" (color . 1) (ltype . "DASHED2") (lts . 5.0) (lw . 50) (gw . 0.025) (ltgen . T)) ("Achurado" (color . 71) (pattern . "SOLID") (ltype . "Continuous") (lts . 1.0) (lw . 50) (hscale . 0.013)) ("Matriz" (color . 5) (ltype . "Continuous") (lts . 1.0) (lw . 50) (gw . 0.040) (ltgen . nil)) ("Rios" (color . 4) (ltype . "Continuous") (lts . 0.2) (lw . 40) (gw . 0.025) (ltgen . nil)))
  ("200" ("Derecho" (color . 230) (ltype . "Continuous") (lts . 0.2) (lw . 40) (gw . 0.100) (ltgen . nil)) ("Eje" (color . 24) (ltype . "DASHDOT") (lts . 0.2) (lw . 40) (gw . 0.050) (ltgen . T)) ("Predios" (color . 64) (ltype . "Continuous") (lts . 1.0) (lw . -3) (gw . 0.040) (ltgen . nil)) ("Afectada" (color . 1) (ltype . "DASHED2") (lts . 5.0) (lw . 50) (gw . 0.040) (ltgen . T)) ("Achurado" (color . 71) (pattern . "SOLID") (ltype . "Continuous") (lts . 1.0) (lw . 50) (hscale . 0.020)) ("Matriz" (color . 5) (ltype . "Continuous") (lts . 1.0) (lw . 50) (gw . 0.064) (ltgen . nil)) ("Rios" (color . 4) (ltype . "Continuous") (lts . 0.2) (lw . 40) (gw . 0.040) (ltgen . nil)))
  ("250" ("Derecho" (color . 230) (ltype . "Continuous") (lts . 0.2) (lw . 40) (gw . 0.125) (ltgen . nil)) ("Eje" (color . 24) (ltype . "DASHDOT") (lts . 0.2) (lw . 40) (gw . 0.063) (ltgen . T)) ("Predios" (color . 64) (ltype . "Continuous") (lts . 1.0) (lw . -3) (gw . 0.050) (ltgen . nil)) ("Afectada" (color . 1) (ltype . "DASHED2") (lts . 5.0) (lw . 50) (gw . 0.050) (ltgen . T)) ("Achurado" (color . 71) (pattern . "SOLID") (ltype . "Continuous") (lts . 1.0) (lw . 50) (hscale . 0.025)) ("Matriz" (color . 5) (ltype . "Continuous") (lts . 1.0) (lw . 50) (gw . 0.080) (ltgen . nil)) ("Rios" (color . 4) (ltype . "Continuous") (lts . 0.2) (lw . 40) (gw . 0.050) (ltgen . nil)))
  ("500" ("Derecho" (color . 230) (ltype . "Continuous") (lts . 0.2) (lw . 40) (gw . 0.250) (ltgen . nil)) ("Eje" (color . 24) (ltype . "DASHDOT") (lts . 0.2) (lw . 40) (gw . 0.125) (ltgen . T)) ("Predios" (color . 64) (ltype . "Continuous") (lts . 1.0) (lw . -3) (gw . 0.100) (ltgen . nil)) ("Afectada" (color . 1) (ltype . "DASHED2") (lts . 5.0) (lw . 50) (gw . 0.100) (ltgen . T)) ("Achurado" (color . 71) (pattern . "SOLID") (ltype . "Continuous") (lts . 1.0) (lw . 50) (hscale . 0.050)) ("Matriz" (color . 5) (ltype . "Continuous") (lts . 1.0) (lw . 50) (gw . 0.160) (ltgen . nil)) ("Rios" (color . 4) (ltype . "Continuous") (lts . 0.2) (lw . 40) (gw . 0.100) (ltgen . nil)))
  ("750" ("Derecho" (color . 230) (ltype . "Continuous") (lts . 0.2) (lw . 40) (gw . 0.375) (ltgen . nil)) ("Eje" (color . 24) (ltype . "DASHDOT") (lts . 0.2) (lw . 40) (gw . 0.188) (ltgen . T)) ("Predios" (color . 64) (ltype . "Continuous") (lts . 1.0) (lw . -3) (gw . 0.150) (ltgen . nil)) ("Afectada" (color . 1) (ltype . "DASHED2") (lts . 5.0) (lw . 50) (gw . 0.150) (ltgen . T)) ("Achurado" (color . 71) (pattern . "SOLID") (ltype . "Continuous") (lts . 1.0) (lw . 50) (hscale . 0.075)) ("Matriz" (color . 5) (ltype . "Continuous") (lts . 1.0) (lw . 50) (gw . 0.240) (ltgen . nil)) ("Rios" (color . 4) (ltype . "Continuous") (lts . 0.2) (lw . 40) (gw . 0.150) (ltgen . nil)))
  ("1000" ("Derecho" (color . 230) (ltype . "Continuous") (lts . 0.2) (lw . 40) (gw . 0.500) (ltgen . nil)) ("Eje" (color . 24) (ltype . "DASHDOT") (lts . 0.2) (lw . 40) (gw . 0.250) (ltgen . T)) ("Predios" (color . 64) (ltype . "Continuous") (lts . 1.0) (lw . -3) (gw . 0.200) (ltgen . nil)) ("Afectada" (color . 1) (ltype . "DASHED2") (lts . 5.0) (lw . 50) (gw . 0.200) (ltgen . T)) ("Achurado" (color . 71) (pattern . "SOLID") (ltype . "Continuous") (lts . 1.0) (lw . 50) (hscale . 0.100)) ("Matriz" (color . 5) (ltype . "Continuous") (lts . 1.0) (lw . 50) (gw . 0.320) (ltgen . nil)) ("Rios" (color . 4) (ltype . "Continuous") (lts . 0.2) (lw . 40) (gw . 0.200) (ltgen . nil)))
  ("1250" ("Derecho" (color . 230) (ltype . "Continuous") (lts . 0.2) (lw . 40) (gw . 0.625) (ltgen . nil)) ("Eje" (color . 24) (ltype . "DASHDOT") (lts . 0.2) (lw . 40) (gw . 0.313) (ltgen . T)) ("Predios" (color . 64) (ltype . "Continuous") (lts . 1.0) (lw . -3) (gw . 0.250) (ltgen . nil)) ("Afectada" (color . 1) (ltype . "DASHED2") (lts . 5.0) (lw . 50) (gw . 0.250) (ltgen . T)) ("Achurado" (color . 71) (pattern . "SOLID") (ltype . "Continuous") (lts . 1.0) (lw . 50) (hscale . 0.125)) ("Matriz" (color . 5) (ltype . "Continuous") (lts . 1.0) (lw . 50) (gw . 0.400) (ltgen . nil)) ("Rios" (color . 4) (ltype . "Continuous") (lts . 0.2) (lw . 40) (gw . 0.250) (ltgen . nil)))
  ("2000" ("Derecho" (color . 230) (ltype . "Continuous") (lts . 0.2) (lw . 40) (gw . 1.000) (ltgen . nil)) ("Eje" (color . 24) (ltype . "DASHDOT") (lts . 0.2) (lw . 40) (gw . 0.500) (ltgen . T)) ("Predios" (color . 64) (ltype . "Continuous") (lts . 1.0) (lw . -3) (gw . 0.400) (ltgen . nil)) ("Afectada" (color . 1) (ltype . "DASHED2") (lts . 5.0) (lw . 50) (gw . 0.400) (ltgen . T)) ("Achurado" (color . 71) (pattern . "SOLID") (ltype . "Continuous") (lts . 1.0) (lw . 50) (hscale . 0.200)) ("Matriz" (color . 5) (ltype . "Continuous") (lts . 1.0) (lw . 50) (gw . 0.640) (ltgen . nil)) ("Rios" (color . 4) (ltype . "Continuous") (lts . 0.2) (lw . 40) (gw . 0.400) (ltgen . nil)))
  ("2500" ("Derecho" (color . 230) (ltype . "Continuous") (lts . 0.2) (lw . 40) (gw . 1.250) (ltgen . nil)) ("Eje" (color . 24) (ltype . "DASHDOT") (lts . 0.2) (lw . 40) (gw . 0.625) (ltgen . T)) ("Predios" (color . 64) (ltype . "Continuous") (lts . 1.0) (lw . -3) (gw . 0.500) (ltgen . nil)) ("Afectada" (color . 1) (ltype . "DASHED2") (lts . 5.0) (lw . 50) (gw . 0.500) (ltgen . T)) ("Achurado" (color . 71) (pattern . "SOLID") (ltype . "Continuous") (lts . 1.0) (lw . 50) (hscale . 0.250)) ("Matriz" (color . 5) (ltype . "Continuous") (lts . 1.0) (lw . 50) (gw . 0.800) (ltgen . nil)) ("Rios" (color . 4) (ltype . "Continuous") (lts . 0.2) (lw . 40) (gw . 0.500) (ltgen . nil)))
  ("5000" ("Derecho" (color . 230) (ltype . "Continuous") (lts . 0.2) (lw . 40) (gw . 2.500) (ltgen . nil)) ("Eje" (color . 24) (ltype . "DASHDOT") (lts . 0.2) (lw . 40) (gw . 1.250) (ltgen . T)) ("Predios" (color . 64) (ltype . "Continuous") (lts . 1.0) (lw . -3) (gw . 1.000) (ltgen . nil)) ("Afectada" (color . 1) (ltype . "DASHED2") (lts . 5.0) (lw . 50) (gw . 1.000) (ltgen . T)) ("Achurado" (color . 71) (pattern . "SOLID") (ltype . "Continuous") (lts . 1.0) (lw . 50) (hscale . 0.500)) ("Matriz" (color . 5) (ltype . "Continuous") (lts . 1.0) (lw . 50) (gw . 1.600) (ltgen . nil)) ("Rios" (color . 4) (ltype . "Continuous") (lts . 0.2) (lw . 40) (gw . 1.000) (ltgen . nil)))
  ("7500" ("Derecho" (color . 230) (ltype . "Continuous") (lts . 0.2) (lw . 40) (gw . 3.750) (ltgen . nil)) ("Eje" (color . 24) (ltype . "DASHDOT") (lts . 0.2) (lw . 40) (gw . 1.875) (ltgen . T)) ("Predios" (color . 64) (ltype . "Continuous") (lts . 1.0) (lw . -3) (gw . 1.500) (ltgen . nil)) ("Afectada" (color . 1) (ltype . "DASHED2") (lts . 5.0) (lw . 50) (gw . 1.500) (ltgen . T)) ("Achurado" (color . 71) (pattern . "SOLID") (ltype . "Continuous") (lts . 1.0) (lw . 50) (hscale . 0.750)) ("Matriz" (color . 5) (ltype . "Continuous") (lts . 1.0) (lw . 50) (gw . 2.400) (ltgen . nil)) ("Rios" (color . 4) (ltype . "Continuous") (lts . 0.2) (lw . 40) (gw . 1.500) (ltgen . nil)))
  ("10000" ("Derecho" (color . 230) (ltype . "Continuous") (lts . 0.2) (lw . 40) (gw . 5.000) (ltgen . nil)) ("Eje" (color . 24) (ltype . "DASHDOT") (lts . 0.2) (lw . 40) (gw . 2.500) (ltgen . T)) ("Predios" (color . 64) (ltype . "Continuous") (lts . 1.0) (lw . -3) (gw . 2.000) (ltgen . nil)) ("Afectada" (color . 1) (ltype . "DASHED2") (lts . 5.0) (lw . 50) (gw . 2.000) (ltgen . T)) ("Achurado" (color . 71) (pattern . "SOLID") (ltype . "Continuous") (lts . 1.0) (lw . 50) (hscale . 1.000)) ("Matriz" (color . 5) (ltype . "Continuous") (lts . 1.0) (lw . 50) (gw . 3.200) (ltgen . nil)) ("Rios" (color . 4) (ltype . "Continuous") (lts . 0.2) (lw . 40) (gw . 2.000) (ltgen . nil)))
  ("12500" ("Derecho" (color . 230) (ltype . "Continuous") (lts . 0.2) (lw . 40) (gw . 6.250) (ltgen . nil)) ("Eje" (color . 24) (ltype . "DASHDOT") (lts . 0.2) (lw . 40) (gw . 3.125) (ltgen . T)) ("Predios" (color . 64) (ltype . "Continuous") (lts . 1.0) (lw . -3) (gw . 2.500) (ltgen . nil)) ("Afectada" (color . 1) (ltype . "DASHED2") (lts . 5.0) (lw . 50) (gw . 2.500) (ltgen . T)) ("Achurado" (color . 71) (pattern . "SOLID") (ltype . "Continuous") (lts . 1.0) (lw . 50) (hscale . 1.250)) ("Matriz" (color . 5) (ltype . "Continuous") (lts . 1.0) (lw . 50) (gw . 4.000) (ltgen . nil)) ("Rios" (color . 4) (ltype . "Continuous") (lts . 0.2) (lw . 40) (gw . 2.500) (ltgen . nil)))
  ("20000" ("Derecho" (color . 230) (ltype . "Continuous") (lts . 0.2) (lw . 40) (gw . 10.000) (ltgen . nil)) ("Eje" (color . 24) (ltype . "DASHDOT") (lts . 0.2) (lw . 40) (gw . 5.000) (ltgen . T)) ("Predios" (color . 64) (ltype . "Continuous") (lts . 1.0) (lw . -3) (gw . 4.000) (ltgen . nil)) ("Afectada" (color . 1) (ltype . "DASHED2") (lts . 5.0) (lw . 50) (gw . 4.000) (ltgen . T)) ("Achurado" (color . 71) (pattern . "SOLID") (ltype . "Continuous") (lts . 1.0) (lw . 50) (hscale . 2.000)) ("Matriz" (color . 5) (ltype . "Continuous") (lts . 1.0) (lw . 50) (gw . 6.400) (ltgen . nil)) ("Rios" (color . 4) (ltype . "Continuous") (lts . 0.2) (lw . 40) (gw . 4.000) (ltgen . nil)))
  ("25000" ("Derecho" (color . 230) (ltype . "Continuous") (lts . 0.2) (lw . 40) (gw . 12.500) (ltgen . nil)) ("Eje" (color . 24) (ltype . "DASHDOT") (lts . 0.2) (lw . 40) (gw . 6.250) (ltgen . T)) ("Predios" (color . 64) (ltype . "Continuous") (lts . 1.0) (lw . -3) (gw . 5.000) (ltgen . nil)) ("Afectada" (color . 1) (ltype . "DASHED2") (lts . 5.0) (lw . 50) (gw . 5.000) (ltgen . T)) ("Achurado" (color . 71) (pattern . "SOLID") (ltype . "Continuous") (lts . 1.0) (lw . 50) (hscale . 2.500)) ("Matriz" (color . 5) (ltype . "Continuous") (lts . 1.0) (lw . 50) (gw . 8.000) (ltgen . nil)) ("Rios" (color . 4) (ltype . "Continuous") (lts . 0.2) (lw . 40) (gw . 5.000) (ltgen . nil)))
))

(setq *UBI_STYLE_MAP_DIAGNOSTICO* '( ;; BR 2026-09-21: tabla literal ESCALAS.xlsx hoja DIAGNOSTICO (20 escalas). Afectada=Directa Magenta; Achurado DOTS/200; +Indirecta/Remanente/Obra(163,163,163). Sin cambios de logica.
  ("20" ("Derecho" (color . 230) (ltype . "Continuous") (lts . 0.2) (lw . 40) (gw . 0.01) (ltgen . nil)) ("Eje" (color . 24) (ltype . "DASHDOT") (lts . 0.2) (lw . 40) (gw . 0.005) (ltgen . T)) ("Predios" (color . 64) (ltype . "Continuous") (lts . 1) (lw . -3) (gw . 0.004) (ltgen . nil)) ("Afectada" (color . 6) (ltype . "Continuous") (lts . 1) (lw . -3) (gw . 0.01) (ltgen . nil)) ("Achurado" (color . 200) (pattern . "DOTS") (ltype . "Continuous") (lts . 1) (lw . -3) (hscale . 0.01)) ("Indirecta" (color . 1) (ltype . "Continuous") (lts . 1) (lw . -3) (gw . 0.01) (ltgen . nil)) ("Remanente" (color . 3) (ltype . "Continuous") (lts . 1) (lw . -3) (gw . 0.002) (ltgen . nil)) ("Matriz" (color . 5) (ltype . "Continuous") (lts . 1) (lw . -3) (gw . 0.01) (ltgen . nil)) ("Via" (color . 0) (ltype . "Continuous") (lts . 0.2) (lw . 40) (gw . 0) (ltgen . nil)) ("Rios" (color . 4) (ltype . "Continuous") (lts . 0.2) (lw . 40) (gw . 0.004) (ltgen . nil)) ("Vivienda" (color . 5) (ltype . "Continuous") (lts . 1.0) (lw . -3) (gw . 0) (ltgen . nil)) ("Obra" (color . 0) (rgb 163 163 163) (ltype . "Continuous") (lts . 1) (lw . -3) (gw . 0) (ltgen . nil)))
  ("25" ("Derecho" (color . 230) (ltype . "Continuous") (lts . 0.2) (lw . 40) (gw . 0.013) (ltgen . nil)) ("Eje" (color . 24) (ltype . "DASHDOT") (lts . 0.2) (lw . 40) (gw . 0.006) (ltgen . T)) ("Predios" (color . 64) (ltype . "Continuous") (lts . 1) (lw . -3) (gw . 0.005) (ltgen . nil)) ("Afectada" (color . 6) (ltype . "Continuous") (lts . 1) (lw . -3) (gw . 0.013) (ltgen . nil)) ("Achurado" (color . 200) (pattern . "DOTS") (ltype . "Continuous") (lts . 1) (lw . -3) (hscale . 0.013)) ("Indirecta" (color . 1) (ltype . "Continuous") (lts . 1) (lw . -3) (gw . 0.013) (ltgen . nil)) ("Remanente" (color . 3) (ltype . "Continuous") (lts . 1) (lw . -3) (gw . 0.003) (ltgen . nil)) ("Matriz" (color . 5) (ltype . "Continuous") (lts . 1) (lw . -3) (gw . 0.013) (ltgen . nil)) ("Via" (color . 0) (ltype . "Continuous") (lts . 0.2) (lw . 40) (gw . 0) (ltgen . nil)) ("Rios" (color . 4) (ltype . "Continuous") (lts . 0.2) (lw . 40) (gw . 0.005) (ltgen . nil)) ("Vivienda" (color . 5) (ltype . "Continuous") (lts . 1.0) (lw . -3) (gw . 0) (ltgen . nil)) ("Obra" (color . 0) (rgb 163 163 163) (ltype . "Continuous") (lts . 1) (lw . -3) (gw . 0) (ltgen . nil)))
  ("50" ("Derecho" (color . 230) (ltype . "Continuous") (lts . 0.2) (lw . 40) (gw . 0.025) (ltgen . nil)) ("Eje" (color . 24) (ltype . "DASHDOT") (lts . 0.2) (lw . 40) (gw . 0.013) (ltgen . T)) ("Predios" (color . 64) (ltype . "Continuous") (lts . 1) (lw . -3) (gw . 0.01) (ltgen . nil)) ("Afectada" (color . 6) (ltype . "Continuous") (lts . 1) (lw . -3) (gw . 0.025) (ltgen . nil)) ("Achurado" (color . 200) (pattern . "DOTS") (ltype . "Continuous") (lts . 1) (lw . -3) (hscale . 0.025)) ("Indirecta" (color . 1) (ltype . "Continuous") (lts . 1) (lw . -3) (gw . 0.025) (ltgen . nil)) ("Remanente" (color . 3) (ltype . "Continuous") (lts . 1) (lw . -3) (gw . 0.005) (ltgen . nil)) ("Matriz" (color . 5) (ltype . "Continuous") (lts . 1) (lw . -3) (gw . 0.025) (ltgen . nil)) ("Via" (color . 0) (ltype . "Continuous") (lts . 0.2) (lw . 40) (gw . 0) (ltgen . nil)) ("Rios" (color . 4) (ltype . "Continuous") (lts . 0.2) (lw . 40) (gw . 0.01) (ltgen . nil)) ("Vivienda" (color . 5) (ltype . "Continuous") (lts . 1.0) (lw . -3) (gw . 0) (ltgen . nil)) ("Obra" (color . 0) (rgb 163 163 163) (ltype . "Continuous") (lts . 1) (lw . -3) (gw . 0) (ltgen . nil)))
  ("75" ("Derecho" (color . 230) (ltype . "Continuous") (lts . 0.2) (lw . 40) (gw . 0.038) (ltgen . nil)) ("Eje" (color . 24) (ltype . "DASHDOT") (lts . 0.2) (lw . 40) (gw . 0.019) (ltgen . T)) ("Predios" (color . 64) (ltype . "Continuous") (lts . 1) (lw . -3) (gw . 0.015) (ltgen . nil)) ("Afectada" (color . 6) (ltype . "Continuous") (lts . 1) (lw . -3) (gw . 0.038) (ltgen . nil)) ("Achurado" (color . 200) (pattern . "DOTS") (ltype . "Continuous") (lts . 1) (lw . -3) (hscale . 0.038)) ("Indirecta" (color . 1) (ltype . "Continuous") (lts . 1) (lw . -3) (gw . 0.038) (ltgen . nil)) ("Remanente" (color . 3) (ltype . "Continuous") (lts . 1) (lw . -3) (gw . 0.008) (ltgen . nil)) ("Matriz" (color . 5) (ltype . "Continuous") (lts . 1) (lw . -3) (gw . 0.038) (ltgen . nil)) ("Via" (color . 0) (ltype . "Continuous") (lts . 0.2) (lw . 40) (gw . 0) (ltgen . nil)) ("Rios" (color . 4) (ltype . "Continuous") (lts . 0.2) (lw . 40) (gw . 0.015) (ltgen . nil)) ("Vivienda" (color . 5) (ltype . "Continuous") (lts . 1.0) (lw . -3) (gw . 0) (ltgen . nil)) ("Obra" (color . 0) (rgb 163 163 163) (ltype . "Continuous") (lts . 1) (lw . -3) (gw . 0) (ltgen . nil)))
  ("100" ("Derecho" (color . 230) (ltype . "Continuous") (lts . 0.2) (lw . 40) (gw . 0.05) (ltgen . nil)) ("Eje" (color . 24) (ltype . "DASHDOT") (lts . 0.2) (lw . 40) (gw . 0.025) (ltgen . T)) ("Predios" (color . 64) (ltype . "Continuous") (lts . 1) (lw . -3) (gw . 0.02) (ltgen . nil)) ("Afectada" (color . 6) (ltype . "Continuous") (lts . 1) (lw . -3) (gw . 0.05) (ltgen . nil)) ("Achurado" (color . 200) (pattern . "DOTS") (ltype . "Continuous") (lts . 1) (lw . -3) (hscale . 0.05)) ("Indirecta" (color . 1) (ltype . "Continuous") (lts . 1) (lw . -3) (gw . 0.05) (ltgen . nil)) ("Remanente" (color . 3) (ltype . "Continuous") (lts . 1) (lw . -3) (gw . 0.01) (ltgen . nil)) ("Matriz" (color . 5) (ltype . "Continuous") (lts . 1) (lw . -3) (gw . 0.05) (ltgen . nil)) ("Via" (color . 0) (ltype . "Continuous") (lts . 0.2) (lw . 40) (gw . 0) (ltgen . nil)) ("Rios" (color . 4) (ltype . "Continuous") (lts . 0.2) (lw . 40) (gw . 0.02) (ltgen . nil)) ("Vivienda" (color . 5) (ltype . "Continuous") (lts . 1.0) (lw . -3) (gw . 0) (ltgen . nil)) ("Obra" (color . 0) (rgb 163 163 163) (ltype . "Continuous") (lts . 1) (lw . -3) (gw . 0) (ltgen . nil)))
  ("125" ("Derecho" (color . 230) (ltype . "Continuous") (lts . 0.2) (lw . 40) (gw . 0.063) (ltgen . nil)) ("Eje" (color . 24) (ltype . "DASHDOT") (lts . 0.2) (lw . 40) (gw . 0.031) (ltgen . T)) ("Predios" (color . 64) (ltype . "Continuous") (lts . 1) (lw . -3) (gw . 0.025) (ltgen . nil)) ("Afectada" (color . 6) (ltype . "Continuous") (lts . 1) (lw . -3) (gw . 0.063) (ltgen . nil)) ("Achurado" (color . 200) (pattern . "DOTS") (ltype . "Continuous") (lts . 1) (lw . -3) (hscale . 0.063)) ("Indirecta" (color . 1) (ltype . "Continuous") (lts . 1) (lw . -3) (gw . 0.063) (ltgen . nil)) ("Remanente" (color . 3) (ltype . "Continuous") (lts . 1) (lw . -3) (gw . 0.013) (ltgen . nil)) ("Matriz" (color . 5) (ltype . "Continuous") (lts . 1) (lw . -3) (gw . 0.063) (ltgen . nil)) ("Via" (color . 0) (ltype . "Continuous") (lts . 0.2) (lw . 40) (gw . 0) (ltgen . nil)) ("Rios" (color . 4) (ltype . "Continuous") (lts . 0.2) (lw . 40) (gw . 0.025) (ltgen . nil)) ("Vivienda" (color . 5) (ltype . "Continuous") (lts . 1.0) (lw . -3) (gw . 0) (ltgen . nil)) ("Obra" (color . 0) (rgb 163 163 163) (ltype . "Continuous") (lts . 1) (lw . -3) (gw . 0) (ltgen . nil)))
  ("200" ("Derecho" (color . 230) (ltype . "Continuous") (lts . 0.2) (lw . 40) (gw . 0.1) (ltgen . nil)) ("Eje" (color . 24) (ltype . "DASHDOT") (lts . 0.2) (lw . 40) (gw . 0.05) (ltgen . T)) ("Predios" (color . 64) (ltype . "Continuous") (lts . 1) (lw . -3) (gw . 0.04) (ltgen . nil)) ("Afectada" (color . 6) (ltype . "Continuous") (lts . 1) (lw . -3) (gw . 0.1) (ltgen . nil)) ("Achurado" (color . 200) (pattern . "DOTS") (ltype . "Continuous") (lts . 1) (lw . -3) (hscale . 0.1)) ("Indirecta" (color . 1) (ltype . "Continuous") (lts . 1) (lw . -3) (gw . 0.1) (ltgen . nil)) ("Remanente" (color . 3) (ltype . "Continuous") (lts . 1) (lw . -3) (gw . 0.02) (ltgen . nil)) ("Matriz" (color . 5) (ltype . "Continuous") (lts . 1) (lw . -3) (gw . 0.1) (ltgen . nil)) ("Via" (color . 0) (ltype . "Continuous") (lts . 0.2) (lw . 40) (gw . 0) (ltgen . nil)) ("Rios" (color . 4) (ltype . "Continuous") (lts . 0.2) (lw . 40) (gw . 0.04) (ltgen . nil)) ("Vivienda" (color . 5) (ltype . "Continuous") (lts . 1.0) (lw . -3) (gw . 0) (ltgen . nil)) ("Obra" (color . 0) (rgb 163 163 163) (ltype . "Continuous") (lts . 1) (lw . -3) (gw . 0) (ltgen . nil)))
  ("250" ("Derecho" (color . 230) (ltype . "Continuous") (lts . 0.2) (lw . 40) (gw . 0.125) (ltgen . nil)) ("Eje" (color . 24) (ltype . "DASHDOT") (lts . 0.2) (lw . 40) (gw . 0.063) (ltgen . T)) ("Predios" (color . 64) (ltype . "Continuous") (lts . 1) (lw . -3) (gw . 0.05) (ltgen . nil)) ("Afectada" (color . 6) (ltype . "Continuous") (lts . 1) (lw . -3) (gw . 0.125) (ltgen . nil)) ("Achurado" (color . 200) (pattern . "DOTS") (ltype . "Continuous") (lts . 1) (lw . -3) (hscale . 0.125)) ("Indirecta" (color . 1) (ltype . "Continuous") (lts . 1) (lw . -3) (gw . 0.125) (ltgen . nil)) ("Remanente" (color . 3) (ltype . "Continuous") (lts . 1) (lw . -3) (gw . 0.025) (ltgen . nil)) ("Matriz" (color . 5) (ltype . "Continuous") (lts . 1) (lw . -3) (gw . 0.125) (ltgen . nil)) ("Via" (color . 0) (ltype . "Continuous") (lts . 0.2) (lw . 40) (gw . 0) (ltgen . nil)) ("Rios" (color . 4) (ltype . "Continuous") (lts . 0.2) (lw . 40) (gw . 0.05) (ltgen . nil)) ("Vivienda" (color . 5) (ltype . "Continuous") (lts . 1.0) (lw . -3) (gw . 0) (ltgen . nil)) ("Obra" (color . 0) (rgb 163 163 163) (ltype . "Continuous") (lts . 1) (lw . -3) (gw . 0) (ltgen . nil)))
  ("500" ("Derecho" (color . 230) (ltype . "Continuous") (lts . 0.2) (lw . 40) (gw . 0.25) (ltgen . nil)) ("Eje" (color . 24) (ltype . "DASHDOT") (lts . 0.2) (lw . 40) (gw . 0.125) (ltgen . T)) ("Predios" (color . 64) (ltype . "Continuous") (lts . 1) (lw . -3) (gw . 0.1) (ltgen . nil)) ("Afectada" (color . 6) (ltype . "Continuous") (lts . 1) (lw . -3) (gw . 0.25) (ltgen . nil)) ("Achurado" (color . 200) (pattern . "DOTS") (ltype . "Continuous") (lts . 1) (lw . -3) (hscale . 0.25)) ("Indirecta" (color . 1) (ltype . "Continuous") (lts . 1) (lw . -3) (gw . 0.25) (ltgen . nil)) ("Remanente" (color . 3) (ltype . "Continuous") (lts . 1) (lw . -3) (gw . 0.05) (ltgen . nil)) ("Matriz" (color . 5) (ltype . "Continuous") (lts . 1) (lw . -3) (gw . 0.25) (ltgen . nil)) ("Via" (color . 0) (ltype . "Continuous") (lts . 0.2) (lw . 40) (gw . 0) (ltgen . nil)) ("Rios" (color . 4) (ltype . "Continuous") (lts . 0.2) (lw . 40) (gw . 0.1) (ltgen . nil)) ("Vivienda" (color . 5) (ltype . "Continuous") (lts . 1.0) (lw . -3) (gw . 0) (ltgen . nil)) ("Obra" (color . 0) (rgb 163 163 163) (ltype . "Continuous") (lts . 1) (lw . -3) (gw . 0) (ltgen . nil)))
  ("750" ("Derecho" (color . 230) (ltype . "Continuous") (lts . 0.2) (lw . 40) (gw . 0.375) (ltgen . nil)) ("Eje" (color . 24) (ltype . "DASHDOT") (lts . 0.2) (lw . 40) (gw . 0.188) (ltgen . T)) ("Predios" (color . 64) (ltype . "Continuous") (lts . 1) (lw . -3) (gw . 0.15) (ltgen . nil)) ("Afectada" (color . 6) (ltype . "Continuous") (lts . 1) (lw . -3) (gw . 0.375) (ltgen . nil)) ("Achurado" (color . 200) (pattern . "DOTS") (ltype . "Continuous") (lts . 1) (lw . -3) (hscale . 0.375)) ("Indirecta" (color . 1) (ltype . "Continuous") (lts . 1) (lw . -3) (gw . 0.375) (ltgen . nil)) ("Remanente" (color . 3) (ltype . "Continuous") (lts . 1) (lw . -3) (gw . 0.075) (ltgen . nil)) ("Matriz" (color . 5) (ltype . "Continuous") (lts . 1) (lw . -3) (gw . 0.375) (ltgen . nil)) ("Via" (color . 0) (ltype . "Continuous") (lts . 0.2) (lw . 40) (gw . 0) (ltgen . nil)) ("Rios" (color . 4) (ltype . "Continuous") (lts . 0.2) (lw . 40) (gw . 0.15) (ltgen . nil)) ("Vivienda" (color . 5) (ltype . "Continuous") (lts . 1.0) (lw . -3) (gw . 0) (ltgen . nil)) ("Obra" (color . 0) (rgb 163 163 163) (ltype . "Continuous") (lts . 1) (lw . -3) (gw . 0) (ltgen . nil)))
  ("1000" ("Derecho" (color . 230) (ltype . "Continuous") (lts . 0.2) (lw . 40) (gw . 0.5) (ltgen . nil)) ("Eje" (color . 24) (ltype . "DASHDOT") (lts . 0.2) (lw . 40) (gw . 0.25) (ltgen . T)) ("Predios" (color . 64) (ltype . "Continuous") (lts . 1) (lw . -3) (gw . 0.2) (ltgen . nil)) ("Afectada" (color . 6) (ltype . "Continuous") (lts . 1) (lw . -3) (gw . 0.5) (ltgen . nil)) ("Achurado" (color . 200) (pattern . "DOTS") (ltype . "Continuous") (lts . 1) (lw . -3) (hscale . 0.5)) ("Indirecta" (color . 1) (ltype . "Continuous") (lts . 1) (lw . -3) (gw . 0.5) (ltgen . nil)) ("Remanente" (color . 3) (ltype . "Continuous") (lts . 1) (lw . -3) (gw . 0.1) (ltgen . nil)) ("Matriz" (color . 5) (ltype . "Continuous") (lts . 1) (lw . -3) (gw . 0.5) (ltgen . nil)) ("Via" (color . 0) (ltype . "Continuous") (lts . 0.2) (lw . 40) (gw . 0) (ltgen . nil)) ("Rios" (color . 4) (ltype . "Continuous") (lts . 0.2) (lw . 40) (gw . 0.2) (ltgen . nil)) ("Vivienda" (color . 5) (ltype . "Continuous") (lts . 1.0) (lw . -3) (gw . 0) (ltgen . nil)) ("Obra" (color . 0) (rgb 163 163 163) (ltype . "Continuous") (lts . 1) (lw . -3) (gw . 0) (ltgen . nil)))
  ("1250" ("Derecho" (color . 230) (ltype . "Continuous") (lts . 0.2) (lw . 40) (gw . 0.625) (ltgen . nil)) ("Eje" (color . 24) (ltype . "DASHDOT") (lts . 0.2) (lw . 40) (gw . 0.313) (ltgen . T)) ("Predios" (color . 64) (ltype . "Continuous") (lts . 1) (lw . -3) (gw . 0.25) (ltgen . nil)) ("Afectada" (color . 6) (ltype . "Continuous") (lts . 1) (lw . -3) (gw . 0.625) (ltgen . nil)) ("Achurado" (color . 200) (pattern . "DOTS") (ltype . "Continuous") (lts . 1) (lw . -3) (hscale . 0.625)) ("Indirecta" (color . 1) (ltype . "Continuous") (lts . 1) (lw . -3) (gw . 0.625) (ltgen . nil)) ("Remanente" (color . 3) (ltype . "Continuous") (lts . 1) (lw . -3) (gw . 0.125) (ltgen . nil)) ("Matriz" (color . 5) (ltype . "Continuous") (lts . 1) (lw . -3) (gw . 0.625) (ltgen . nil)) ("Via" (color . 0) (ltype . "Continuous") (lts . 0.2) (lw . 40) (gw . 0) (ltgen . nil)) ("Rios" (color . 4) (ltype . "Continuous") (lts . 0.2) (lw . 40) (gw . 0.25) (ltgen . nil)) ("Vivienda" (color . 5) (ltype . "Continuous") (lts . 1.0) (lw . -3) (gw . 0) (ltgen . nil)) ("Obra" (color . 0) (rgb 163 163 163) (ltype . "Continuous") (lts . 1) (lw . -3) (gw . 0) (ltgen . nil)))
  ("2000" ("Derecho" (color . 230) (ltype . "Continuous") (lts . 0.2) (lw . 40) (gw . 1) (ltgen . nil)) ("Eje" (color . 24) (ltype . "DASHDOT") (lts . 0.2) (lw . 40) (gw . 0.5) (ltgen . T)) ("Predios" (color . 64) (ltype . "Continuous") (lts . 1) (lw . -3) (gw . 0.4) (ltgen . nil)) ("Afectada" (color . 6) (ltype . "Continuous") (lts . 1) (lw . -3) (gw . 1) (ltgen . nil)) ("Achurado" (color . 200) (pattern . "DOTS") (ltype . "Continuous") (lts . 1) (lw . -3) (hscale . 1)) ("Indirecta" (color . 1) (ltype . "Continuous") (lts . 1) (lw . -3) (gw . 1) (ltgen . nil)) ("Remanente" (color . 3) (ltype . "Continuous") (lts . 1) (lw . -3) (gw . 0.2) (ltgen . nil)) ("Matriz" (color . 5) (ltype . "Continuous") (lts . 1) (lw . -3) (gw . 1) (ltgen . nil)) ("Via" (color . 0) (ltype . "Continuous") (lts . 0.2) (lw . 40) (gw . 0) (ltgen . nil)) ("Rios" (color . 4) (ltype . "Continuous") (lts . 0.2) (lw . 40) (gw . 0.4) (ltgen . nil)) ("Vivienda" (color . 5) (ltype . "Continuous") (lts . 1.0) (lw . -3) (gw . 0) (ltgen . nil)) ("Obra" (color . 0) (rgb 163 163 163) (ltype . "Continuous") (lts . 1) (lw . -3) (gw . 0) (ltgen . nil)))
  ("2500" ("Derecho" (color . 230) (ltype . "Continuous") (lts . 0.2) (lw . 40) (gw . 1.25) (ltgen . nil)) ("Eje" (color . 24) (ltype . "DASHDOT") (lts . 0.2) (lw . 40) (gw . 0.625) (ltgen . T)) ("Predios" (color . 64) (ltype . "Continuous") (lts . 1) (lw . -3) (gw . 0.5) (ltgen . nil)) ("Afectada" (color . 6) (ltype . "Continuous") (lts . 1) (lw . -3) (gw . 1.25) (ltgen . nil)) ("Achurado" (color . 200) (pattern . "DOTS") (ltype . "Continuous") (lts . 1) (lw . -3) (hscale . 1.25)) ("Indirecta" (color . 1) (ltype . "Continuous") (lts . 1) (lw . -3) (gw . 1.25) (ltgen . nil)) ("Remanente" (color . 3) (ltype . "Continuous") (lts . 1) (lw . -3) (gw . 0.25) (ltgen . nil)) ("Matriz" (color . 5) (ltype . "Continuous") (lts . 1) (lw . -3) (gw . 1.25) (ltgen . nil)) ("Via" (color . 0) (ltype . "Continuous") (lts . 0.2) (lw . 40) (gw . 0) (ltgen . nil)) ("Rios" (color . 4) (ltype . "Continuous") (lts . 0.2) (lw . 40) (gw . 0.5) (ltgen . nil)) ("Vivienda" (color . 5) (ltype . "Continuous") (lts . 1.0) (lw . -3) (gw . 0) (ltgen . nil)) ("Obra" (color . 0) (rgb 163 163 163) (ltype . "Continuous") (lts . 1) (lw . -3) (gw . 0) (ltgen . nil)))
  ("5000" ("Derecho" (color . 230) (ltype . "Continuous") (lts . 0.2) (lw . 40) (gw . 2.5) (ltgen . nil)) ("Eje" (color . 24) (ltype . "DASHDOT") (lts . 0.2) (lw . 40) (gw . 1.25) (ltgen . T)) ("Predios" (color . 64) (ltype . "Continuous") (lts . 1) (lw . -3) (gw . 1) (ltgen . nil)) ("Afectada" (color . 6) (ltype . "Continuous") (lts . 1) (lw . -3) (gw . 2.5) (ltgen . nil)) ("Achurado" (color . 200) (pattern . "DOTS") (ltype . "Continuous") (lts . 1) (lw . -3) (hscale . 2.5)) ("Indirecta" (color . 1) (ltype . "Continuous") (lts . 1) (lw . -3) (gw . 2.5) (ltgen . nil)) ("Remanente" (color . 3) (ltype . "Continuous") (lts . 1) (lw . -3) (gw . 0.5) (ltgen . nil)) ("Matriz" (color . 5) (ltype . "Continuous") (lts . 1) (lw . -3) (gw . 2.5) (ltgen . nil)) ("Via" (color . 0) (ltype . "Continuous") (lts . 0.2) (lw . 40) (gw . 0) (ltgen . nil)) ("Rios" (color . 4) (ltype . "Continuous") (lts . 0.2) (lw . 40) (gw . 1) (ltgen . nil)) ("Vivienda" (color . 5) (ltype . "Continuous") (lts . 1.0) (lw . -3) (gw . 0) (ltgen . nil)) ("Obra" (color . 0) (rgb 163 163 163) (ltype . "Continuous") (lts . 1) (lw . -3) (gw . 0) (ltgen . nil)))
  ("7500" ("Derecho" (color . 230) (ltype . "Continuous") (lts . 0.2) (lw . 40) (gw . 3.75) (ltgen . nil)) ("Eje" (color . 24) (ltype . "DASHDOT") (lts . 0.2) (lw . 40) (gw . 1.875) (ltgen . T)) ("Predios" (color . 64) (ltype . "Continuous") (lts . 1) (lw . -3) (gw . 1.5) (ltgen . nil)) ("Afectada" (color . 6) (ltype . "Continuous") (lts . 1) (lw . -3) (gw . 3.75) (ltgen . nil)) ("Achurado" (color . 200) (pattern . "DOTS") (ltype . "Continuous") (lts . 1) (lw . -3) (hscale . 3.75)) ("Indirecta" (color . 1) (ltype . "Continuous") (lts . 1) (lw . -3) (gw . 3.75) (ltgen . nil)) ("Remanente" (color . 3) (ltype . "Continuous") (lts . 1) (lw . -3) (gw . 0.75) (ltgen . nil)) ("Matriz" (color . 5) (ltype . "Continuous") (lts . 1) (lw . -3) (gw . 3.75) (ltgen . nil)) ("Via" (color . 0) (ltype . "Continuous") (lts . 0.2) (lw . 40) (gw . 0) (ltgen . nil)) ("Rios" (color . 4) (ltype . "Continuous") (lts . 0.2) (lw . 40) (gw . 1.5) (ltgen . nil)) ("Vivienda" (color . 5) (ltype . "Continuous") (lts . 1.0) (lw . -3) (gw . 0) (ltgen . nil)) ("Obra" (color . 0) (rgb 163 163 163) (ltype . "Continuous") (lts . 1) (lw . -3) (gw . 0) (ltgen . nil)))
  ("10000" ("Derecho" (color . 230) (ltype . "Continuous") (lts . 0.2) (lw . 40) (gw . 5) (ltgen . nil)) ("Eje" (color . 24) (ltype . "DASHDOT") (lts . 0.2) (lw . 40) (gw . 2.5) (ltgen . T)) ("Predios" (color . 64) (ltype . "Continuous") (lts . 1) (lw . -3) (gw . 2) (ltgen . nil)) ("Afectada" (color . 6) (ltype . "Continuous") (lts . 1) (lw . -3) (gw . 5) (ltgen . nil)) ("Achurado" (color . 200) (pattern . "DOTS") (ltype . "Continuous") (lts . 1) (lw . -3) (hscale . 5)) ("Indirecta" (color . 1) (ltype . "Continuous") (lts . 1) (lw . -3) (gw . 5) (ltgen . nil)) ("Remanente" (color . 3) (ltype . "Continuous") (lts . 1) (lw . -3) (gw . 1) (ltgen . nil)) ("Matriz" (color . 5) (ltype . "Continuous") (lts . 1) (lw . -3) (gw . 5) (ltgen . nil)) ("Via" (color . 0) (ltype . "Continuous") (lts . 0.2) (lw . 40) (gw . 0) (ltgen . nil)) ("Rios" (color . 4) (ltype . "Continuous") (lts . 0.2) (lw . 40) (gw . 2) (ltgen . nil)) ("Vivienda" (color . 5) (ltype . "Continuous") (lts . 1.0) (lw . -3) (gw . 0) (ltgen . nil)) ("Obra" (color . 0) (rgb 163 163 163) (ltype . "Continuous") (lts . 1) (lw . -3) (gw . 0) (ltgen . nil)))
  ("12500" ("Derecho" (color . 230) (ltype . "Continuous") (lts . 0.2) (lw . 40) (gw . 6.25) (ltgen . nil)) ("Eje" (color . 24) (ltype . "DASHDOT") (lts . 0.2) (lw . 40) (gw . 3.125) (ltgen . T)) ("Predios" (color . 64) (ltype . "Continuous") (lts . 1) (lw . -3) (gw . 2.5) (ltgen . nil)) ("Afectada" (color . 6) (ltype . "Continuous") (lts . 1) (lw . -3) (gw . 6.25) (ltgen . nil)) ("Achurado" (color . 200) (pattern . "DOTS") (ltype . "Continuous") (lts . 1) (lw . -3) (hscale . 6.25)) ("Indirecta" (color . 1) (ltype . "Continuous") (lts . 1) (lw . -3) (gw . 6.25) (ltgen . nil)) ("Remanente" (color . 3) (ltype . "Continuous") (lts . 1) (lw . -3) (gw . 1.25) (ltgen . nil)) ("Matriz" (color . 5) (ltype . "Continuous") (lts . 1) (lw . -3) (gw . 6.25) (ltgen . nil)) ("Via" (color . 0) (ltype . "Continuous") (lts . 0.2) (lw . 40) (gw . 0) (ltgen . nil)) ("Rios" (color . 4) (ltype . "Continuous") (lts . 0.2) (lw . 40) (gw . 2.5) (ltgen . nil)) ("Vivienda" (color . 5) (ltype . "Continuous") (lts . 1.0) (lw . -3) (gw . 0) (ltgen . nil)) ("Obra" (color . 0) (rgb 163 163 163) (ltype . "Continuous") (lts . 1) (lw . -3) (gw . 0) (ltgen . nil)))
  ("20000" ("Derecho" (color . 230) (ltype . "Continuous") (lts . 0.2) (lw . 40) (gw . 10) (ltgen . nil)) ("Eje" (color . 24) (ltype . "DASHDOT") (lts . 0.2) (lw . 40) (gw . 5) (ltgen . T)) ("Predios" (color . 64) (ltype . "Continuous") (lts . 1) (lw . -3) (gw . 4) (ltgen . nil)) ("Afectada" (color . 6) (ltype . "Continuous") (lts . 1) (lw . -3) (gw . 10) (ltgen . nil)) ("Achurado" (color . 200) (pattern . "DOTS") (ltype . "Continuous") (lts . 1) (lw . -3) (hscale . 10)) ("Indirecta" (color . 1) (ltype . "Continuous") (lts . 1) (lw . -3) (gw . 10) (ltgen . nil)) ("Remanente" (color . 3) (ltype . "Continuous") (lts . 1) (lw . -3) (gw . 2) (ltgen . nil)) ("Matriz" (color . 5) (ltype . "Continuous") (lts . 1) (lw . -3) (gw . 10) (ltgen . nil)) ("Via" (color . 0) (ltype . "Continuous") (lts . 0.2) (lw . 40) (gw . 0) (ltgen . nil)) ("Rios" (color . 4) (ltype . "Continuous") (lts . 0.2) (lw . 40) (gw . 4) (ltgen . nil)) ("Vivienda" (color . 5) (ltype . "Continuous") (lts . 1.0) (lw . -3) (gw . 0) (ltgen . nil)) ("Obra" (color . 0) (rgb 163 163 163) (ltype . "Continuous") (lts . 1) (lw . -3) (gw . 0) (ltgen . nil)))
  ("25000" ("Derecho" (color . 230) (ltype . "Continuous") (lts . 0.2) (lw . 40) (gw . 12.5) (ltgen . nil)) ("Eje" (color . 24) (ltype . "DASHDOT") (lts . 0.2) (lw . 40) (gw . 6.25) (ltgen . T)) ("Predios" (color . 64) (ltype . "Continuous") (lts . 1) (lw . -3) (gw . 5) (ltgen . nil)) ("Afectada" (color . 6) (ltype . "Continuous") (lts . 1) (lw . -3) (gw . 12.5) (ltgen . nil)) ("Achurado" (color . 200) (pattern . "DOTS") (ltype . "Continuous") (lts . 1) (lw . -3) (hscale . 12.5)) ("Indirecta" (color . 1) (ltype . "Continuous") (lts . 1) (lw . -3) (gw . 12.5) (ltgen . nil)) ("Remanente" (color . 3) (ltype . "Continuous") (lts . 1) (lw . -3) (gw . 2.5) (ltgen . nil)) ("Matriz" (color . 5) (ltype . "Continuous") (lts . 1) (lw . -3) (gw . 12.5) (ltgen . nil)) ("Via" (color . 0) (ltype . "Continuous") (lts . 0.2) (lw . 40) (gw . 0) (ltgen . nil)) ("Rios" (color . 4) (ltype . "Continuous") (lts . 0.2) (lw . 40) (gw . 5) (ltgen . nil)) ("Vivienda" (color . 5) (ltype . "Continuous") (lts . 1.0) (lw . -3) (gw . 0) (ltgen . nil)) ("Obra" (color . 0) (rgb 163 163 163) (ltype . "Continuous") (lts . 1) (lw . -3) (gw . 0) (ltgen . nil)))
))

(setq *UBI_STYLE_MAP_PERIMETRICO* '( ;; BR 2026-09-21: tabla literal ESCALAS.xlsx hoja PERIMETRICO (solo Derecho/Eje/AF DASHDOT Magenta); resto = UBICACION (fallback documentado).
  ("20" ("Derecho" (color . 230) (ltype . "Continuous") (lts . 0.2) (lw . 40) (gw . 0.01) (ltgen . nil)) ("Eje" (color . 24) (ltype . "DASHDOT") (lts . 0.2) (lw . 40) (gw . 0.005) (ltgen . T)) ("Predios" (color . 64) (ltype . "Continuous") (lts . 1) (lw . -3) (gw . 0.004) (ltgen . nil)) ("Afectada" (color . 6) (ltype . "DASHDOT") (lts . 0.2) (lw . 40) (gw . 0.005) (ltgen . nil)) ("Achurado" (color . 71) (pattern . "SOLID") (ltype . "Continuous") (lts . 1) (lw . 50) (hscale . 0.002)) ("Matriz" (color . 5) (ltype . "Continuous") (lts . 1) (lw . 50) (gw . 0.006) (ltgen . nil)) ("Via" (color . 0) (ltype . "Continuous") (lts . 0.2) (lw . 40) (gw . 0) (ltgen . nil)) ("Rios" (color . 4) (ltype . "Continuous") (lts . 0.2) (lw . 40) (gw . 0.004) (ltgen . nil)))
  ("25" ("Derecho" (color . 230) (ltype . "Continuous") (lts . 0.2) (lw . 40) (gw . 0.013) (ltgen . nil)) ("Eje" (color . 24) (ltype . "DASHDOT") (lts . 0.2) (lw . 40) (gw . 0.006) (ltgen . T)) ("Predios" (color . 64) (ltype . "Continuous") (lts . 1) (lw . -3) (gw . 0.005) (ltgen . nil)) ("Afectada" (color . 6) (ltype . "DASHDOT") (lts . 0.2) (lw . 40) (gw . 0.006) (ltgen . nil)) ("Achurado" (color . 71) (pattern . "SOLID") (ltype . "Continuous") (lts . 1) (lw . 50) (hscale . 0.003)) ("Matriz" (color . 5) (ltype . "Continuous") (lts . 1) (lw . 50) (gw . 0.008) (ltgen . nil)) ("Via" (color . 0) (ltype . "Continuous") (lts . 0.2) (lw . 40) (gw . 0) (ltgen . nil)) ("Rios" (color . 4) (ltype . "Continuous") (lts . 0.2) (lw . 40) (gw . 0.005) (ltgen . nil)))
  ("50" ("Derecho" (color . 230) (ltype . "Continuous") (lts . 0.2) (lw . 40) (gw . 0.025) (ltgen . nil)) ("Eje" (color . 24) (ltype . "DASHDOT") (lts . 0.2) (lw . 40) (gw . 0.013) (ltgen . T)) ("Predios" (color . 64) (ltype . "Continuous") (lts . 1) (lw . -3) (gw . 0.01) (ltgen . nil)) ("Afectada" (color . 6) (ltype . "DASHDOT") (lts . 0.2) (lw . 40) (gw . 0.013) (ltgen . nil)) ("Achurado" (color . 71) (pattern . "SOLID") (ltype . "Continuous") (lts . 1) (lw . 50) (hscale . 0.005)) ("Matriz" (color . 5) (ltype . "Continuous") (lts . 1) (lw . 50) (gw . 0.016) (ltgen . nil)) ("Via" (color . 0) (ltype . "Continuous") (lts . 0.2) (lw . 40) (gw . 0) (ltgen . nil)) ("Rios" (color . 4) (ltype . "Continuous") (lts . 0.2) (lw . 40) (gw . 0.01) (ltgen . nil)))
  ("75" ("Derecho" (color . 230) (ltype . "Continuous") (lts . 0.2) (lw . 40) (gw . 0.038) (ltgen . nil)) ("Eje" (color . 24) (ltype . "DASHDOT") (lts . 0.2) (lw . 40) (gw . 0.019) (ltgen . T)) ("Predios" (color . 64) (ltype . "Continuous") (lts . 1) (lw . -3) (gw . 0.015) (ltgen . nil)) ("Afectada" (color . 6) (ltype . "DASHDOT") (lts . 0.2) (lw . 40) (gw . 0.019) (ltgen . nil)) ("Achurado" (color . 71) (pattern . "SOLID") (ltype . "Continuous") (lts . 1) (lw . 50) (hscale . 0.008)) ("Matriz" (color . 5) (ltype . "Continuous") (lts . 1) (lw . 50) (gw . 0.024) (ltgen . nil)) ("Via" (color . 0) (ltype . "Continuous") (lts . 0.2) (lw . 40) (gw . 0) (ltgen . nil)) ("Rios" (color . 4) (ltype . "Continuous") (lts . 0.2) (lw . 40) (gw . 0.015) (ltgen . nil)))
  ("100" ("Derecho" (color . 230) (ltype . "Continuous") (lts . 0.2) (lw . 40) (gw . 0.05) (ltgen . nil)) ("Eje" (color . 24) (ltype . "DASHDOT") (lts . 0.2) (lw . 40) (gw . 0.025) (ltgen . T)) ("Predios" (color . 64) (ltype . "Continuous") (lts . 1) (lw . -3) (gw . 0.02) (ltgen . nil)) ("Afectada" (color . 6) (ltype . "DASHDOT") (lts . 0.2) (lw . 40) (gw . 0.025) (ltgen . nil)) ("Achurado" (color . 71) (pattern . "SOLID") (ltype . "Continuous") (lts . 1) (lw . 50) (hscale . 0.01)) ("Matriz" (color . 5) (ltype . "Continuous") (lts . 1) (lw . 50) (gw . 0.032) (ltgen . nil)) ("Via" (color . 0) (ltype . "Continuous") (lts . 0.2) (lw . 40) (gw . 0) (ltgen . nil)) ("Rios" (color . 4) (ltype . "Continuous") (lts . 0.2) (lw . 40) (gw . 0.02) (ltgen . nil)))
  ("125" ("Derecho" (color . 230) (ltype . "Continuous") (lts . 0.2) (lw . 40) (gw . 0.063) (ltgen . nil)) ("Eje" (color . 24) (ltype . "DASHDOT") (lts . 0.2) (lw . 40) (gw . 0.031) (ltgen . T)) ("Predios" (color . 64) (ltype . "Continuous") (lts . 1) (lw . -3) (gw . 0.025) (ltgen . nil)) ("Afectada" (color . 6) (ltype . "DASHDOT") (lts . 0.2) (lw . 40) (gw . 0.031) (ltgen . nil)) ("Achurado" (color . 71) (pattern . "SOLID") (ltype . "Continuous") (lts . 1) (lw . 50) (hscale . 0.013)) ("Matriz" (color . 5) (ltype . "Continuous") (lts . 1) (lw . 50) (gw . 0.04) (ltgen . nil)) ("Via" (color . 0) (ltype . "Continuous") (lts . 0.2) (lw . 40) (gw . 0) (ltgen . nil)) ("Rios" (color . 4) (ltype . "Continuous") (lts . 0.2) (lw . 40) (gw . 0.025) (ltgen . nil)))
  ("200" ("Derecho" (color . 230) (ltype . "Continuous") (lts . 0.2) (lw . 40) (gw . 0.1) (ltgen . nil)) ("Eje" (color . 24) (ltype . "DASHDOT") (lts . 0.2) (lw . 40) (gw . 0.05) (ltgen . T)) ("Predios" (color . 64) (ltype . "Continuous") (lts . 1) (lw . -3) (gw . 0.04) (ltgen . nil)) ("Afectada" (color . 6) (ltype . "DASHDOT") (lts . 0.2) (lw . 40) (gw . 0.05) (ltgen . nil)) ("Achurado" (color . 71) (pattern . "SOLID") (ltype . "Continuous") (lts . 1) (lw . 50) (hscale . 0.02)) ("Matriz" (color . 5) (ltype . "Continuous") (lts . 1) (lw . 50) (gw . 0.064) (ltgen . nil)) ("Via" (color . 0) (ltype . "Continuous") (lts . 0.2) (lw . 40) (gw . 0) (ltgen . nil)) ("Rios" (color . 4) (ltype . "Continuous") (lts . 0.2) (lw . 40) (gw . 0.04) (ltgen . nil)))
  ("250" ("Derecho" (color . 230) (ltype . "Continuous") (lts . 0.2) (lw . 40) (gw . 0.125) (ltgen . nil)) ("Eje" (color . 24) (ltype . "DASHDOT") (lts . 0.2) (lw . 40) (gw . 0.063) (ltgen . T)) ("Predios" (color . 64) (ltype . "Continuous") (lts . 1) (lw . -3) (gw . 0.05) (ltgen . nil)) ("Afectada" (color . 6) (ltype . "DASHDOT") (lts . 0.2) (lw . 40) (gw . 0.063) (ltgen . nil)) ("Achurado" (color . 71) (pattern . "SOLID") (ltype . "Continuous") (lts . 1) (lw . 50) (hscale . 0.025)) ("Matriz" (color . 5) (ltype . "Continuous") (lts . 1) (lw . 50) (gw . 0.08) (ltgen . nil)) ("Via" (color . 0) (ltype . "Continuous") (lts . 0.2) (lw . 40) (gw . 0) (ltgen . nil)) ("Rios" (color . 4) (ltype . "Continuous") (lts . 0.2) (lw . 40) (gw . 0.05) (ltgen . nil)))
  ("500" ("Derecho" (color . 230) (ltype . "Continuous") (lts . 0.2) (lw . 40) (gw . 0.25) (ltgen . nil)) ("Eje" (color . 24) (ltype . "DASHDOT") (lts . 0.2) (lw . 40) (gw . 0.125) (ltgen . T)) ("Predios" (color . 64) (ltype . "Continuous") (lts . 1) (lw . -3) (gw . 0.1) (ltgen . nil)) ("Afectada" (color . 6) (ltype . "DASHDOT") (lts . 0.2) (lw . 40) (gw . 0.125) (ltgen . nil)) ("Achurado" (color . 71) (pattern . "SOLID") (ltype . "Continuous") (lts . 1) (lw . 50) (hscale . 0.05)) ("Matriz" (color . 5) (ltype . "Continuous") (lts . 1) (lw . 50) (gw . 0.16) (ltgen . nil)) ("Via" (color . 0) (ltype . "Continuous") (lts . 0.2) (lw . 40) (gw . 0) (ltgen . nil)) ("Rios" (color . 4) (ltype . "Continuous") (lts . 0.2) (lw . 40) (gw . 0.1) (ltgen . nil)))
  ("750" ("Derecho" (color . 230) (ltype . "Continuous") (lts . 0.2) (lw . 40) (gw . 0.375) (ltgen . nil)) ("Eje" (color . 24) (ltype . "DASHDOT") (lts . 0.2) (lw . 40) (gw . 0.188) (ltgen . T)) ("Predios" (color . 64) (ltype . "Continuous") (lts . 1) (lw . -3) (gw . 0.15) (ltgen . nil)) ("Afectada" (color . 6) (ltype . "DASHDOT") (lts . 0.2) (lw . 40) (gw . 0.188) (ltgen . nil)) ("Achurado" (color . 71) (pattern . "SOLID") (ltype . "Continuous") (lts . 1) (lw . 50) (hscale . 0.075)) ("Matriz" (color . 5) (ltype . "Continuous") (lts . 1) (lw . 50) (gw . 0.24) (ltgen . nil)) ("Via" (color . 0) (ltype . "Continuous") (lts . 0.2) (lw . 40) (gw . 0) (ltgen . nil)) ("Rios" (color . 4) (ltype . "Continuous") (lts . 0.2) (lw . 40) (gw . 0.15) (ltgen . nil)))
  ("1000" ("Derecho" (color . 230) (ltype . "Continuous") (lts . 0.2) (lw . 40) (gw . 0.5) (ltgen . nil)) ("Eje" (color . 24) (ltype . "DASHDOT") (lts . 0.2) (lw . 40) (gw . 0.25) (ltgen . T)) ("Predios" (color . 64) (ltype . "Continuous") (lts . 1) (lw . -3) (gw . 0.2) (ltgen . nil)) ("Afectada" (color . 6) (ltype . "DASHDOT") (lts . 0.2) (lw . 40) (gw . 0.25) (ltgen . nil)) ("Achurado" (color . 71) (pattern . "SOLID") (ltype . "Continuous") (lts . 1) (lw . 50) (hscale . 0.1)) ("Matriz" (color . 5) (ltype . "Continuous") (lts . 1) (lw . 50) (gw . 0.32) (ltgen . nil)) ("Via" (color . 0) (ltype . "Continuous") (lts . 0.2) (lw . 40) (gw . 0) (ltgen . nil)) ("Rios" (color . 4) (ltype . "Continuous") (lts . 0.2) (lw . 40) (gw . 0.2) (ltgen . nil)))
  ("1250" ("Derecho" (color . 230) (ltype . "Continuous") (lts . 0.2) (lw . 40) (gw . 0.625) (ltgen . nil)) ("Eje" (color . 24) (ltype . "DASHDOT") (lts . 0.2) (lw . 40) (gw . 0.313) (ltgen . T)) ("Predios" (color . 64) (ltype . "Continuous") (lts . 1) (lw . -3) (gw . 0.25) (ltgen . nil)) ("Afectada" (color . 6) (ltype . "DASHDOT") (lts . 0.2) (lw . 40) (gw . 0.313) (ltgen . nil)) ("Achurado" (color . 71) (pattern . "SOLID") (ltype . "Continuous") (lts . 1) (lw . 50) (hscale . 0.125)) ("Matriz" (color . 5) (ltype . "Continuous") (lts . 1) (lw . 50) (gw . 0.4) (ltgen . nil)) ("Via" (color . 0) (ltype . "Continuous") (lts . 0.2) (lw . 40) (gw . 0) (ltgen . nil)) ("Rios" (color . 4) (ltype . "Continuous") (lts . 0.2) (lw . 40) (gw . 0.25) (ltgen . nil)))
  ("2000" ("Derecho" (color . 230) (ltype . "Continuous") (lts . 0.2) (lw . 40) (gw . 1) (ltgen . nil)) ("Eje" (color . 24) (ltype . "DASHDOT") (lts . 0.2) (lw . 40) (gw . 0.5) (ltgen . T)) ("Predios" (color . 64) (ltype . "Continuous") (lts . 1) (lw . -3) (gw . 0.4) (ltgen . nil)) ("Afectada" (color . 6) (ltype . "DASHDOT") (lts . 0.2) (lw . 40) (gw . 0.5) (ltgen . nil)) ("Achurado" (color . 71) (pattern . "SOLID") (ltype . "Continuous") (lts . 1) (lw . 50) (hscale . 0.2)) ("Matriz" (color . 5) (ltype . "Continuous") (lts . 1) (lw . 50) (gw . 0.64) (ltgen . nil)) ("Via" (color . 0) (ltype . "Continuous") (lts . 0.2) (lw . 40) (gw . 0) (ltgen . nil)) ("Rios" (color . 4) (ltype . "Continuous") (lts . 0.2) (lw . 40) (gw . 0.4) (ltgen . nil)))
  ("2500" ("Derecho" (color . 230) (ltype . "Continuous") (lts . 0.2) (lw . 40) (gw . 1.25) (ltgen . nil)) ("Eje" (color . 24) (ltype . "DASHDOT") (lts . 0.2) (lw . 40) (gw . 0.625) (ltgen . T)) ("Predios" (color . 64) (ltype . "Continuous") (lts . 1) (lw . -3) (gw . 0.5) (ltgen . nil)) ("Afectada" (color . 6) (ltype . "DASHDOT") (lts . 0.2) (lw . 40) (gw . 0.625) (ltgen . nil)) ("Achurado" (color . 71) (pattern . "SOLID") (ltype . "Continuous") (lts . 1) (lw . 50) (hscale . 0.25)) ("Matriz" (color . 5) (ltype . "Continuous") (lts . 1) (lw . 50) (gw . 0.8) (ltgen . nil)) ("Via" (color . 0) (ltype . "Continuous") (lts . 0.2) (lw . 40) (gw . 0) (ltgen . nil)) ("Rios" (color . 4) (ltype . "Continuous") (lts . 0.2) (lw . 40) (gw . 0.5) (ltgen . nil)))
  ("5000" ("Derecho" (color . 230) (ltype . "Continuous") (lts . 0.2) (lw . 40) (gw . 2.5) (ltgen . nil)) ("Eje" (color . 24) (ltype . "DASHDOT") (lts . 0.2) (lw . 40) (gw . 1.25) (ltgen . T)) ("Predios" (color . 64) (ltype . "Continuous") (lts . 1) (lw . -3) (gw . 1) (ltgen . nil)) ("Afectada" (color . 6) (ltype . "DASHDOT") (lts . 0.2) (lw . 40) (gw . 1.25) (ltgen . nil)) ("Achurado" (color . 71) (pattern . "SOLID") (ltype . "Continuous") (lts . 1) (lw . 50) (hscale . 0.5)) ("Matriz" (color . 5) (ltype . "Continuous") (lts . 1) (lw . 50) (gw . 1.6) (ltgen . nil)) ("Via" (color . 0) (ltype . "Continuous") (lts . 0.2) (lw . 40) (gw . 0) (ltgen . nil)) ("Rios" (color . 4) (ltype . "Continuous") (lts . 0.2) (lw . 40) (gw . 1) (ltgen . nil)))
  ("7500" ("Derecho" (color . 230) (ltype . "Continuous") (lts . 0.2) (lw . 40) (gw . 3.75) (ltgen . nil)) ("Eje" (color . 24) (ltype . "DASHDOT") (lts . 0.2) (lw . 40) (gw . 1.875) (ltgen . T)) ("Predios" (color . 64) (ltype . "Continuous") (lts . 1) (lw . -3) (gw . 1.5) (ltgen . nil)) ("Afectada" (color . 6) (ltype . "DASHDOT") (lts . 0.2) (lw . 40) (gw . 1.875) (ltgen . nil)) ("Achurado" (color . 71) (pattern . "SOLID") (ltype . "Continuous") (lts . 1) (lw . 50) (hscale . 0.75)) ("Matriz" (color . 5) (ltype . "Continuous") (lts . 1) (lw . 50) (gw . 2.4) (ltgen . nil)) ("Via" (color . 0) (ltype . "Continuous") (lts . 0.2) (lw . 40) (gw . 0) (ltgen . nil)) ("Rios" (color . 4) (ltype . "Continuous") (lts . 0.2) (lw . 40) (gw . 1.5) (ltgen . nil)))
  ("10000" ("Derecho" (color . 230) (ltype . "Continuous") (lts . 0.2) (lw . 40) (gw . 5) (ltgen . nil)) ("Eje" (color . 24) (ltype . "DASHDOT") (lts . 0.2) (lw . 40) (gw . 2.5) (ltgen . T)) ("Predios" (color . 64) (ltype . "Continuous") (lts . 1) (lw . -3) (gw . 2) (ltgen . nil)) ("Afectada" (color . 6) (ltype . "DASHDOT") (lts . 0.2) (lw . 40) (gw . 2.5) (ltgen . nil)) ("Achurado" (color . 71) (pattern . "SOLID") (ltype . "Continuous") (lts . 1) (lw . 50) (hscale . 1)) ("Matriz" (color . 5) (ltype . "Continuous") (lts . 1) (lw . 50) (gw . 3.2) (ltgen . nil)) ("Via" (color . 0) (ltype . "Continuous") (lts . 0.2) (lw . 40) (gw . 0) (ltgen . nil)) ("Rios" (color . 4) (ltype . "Continuous") (lts . 0.2) (lw . 40) (gw . 2) (ltgen . nil)))
  ("12500" ("Derecho" (color . 230) (ltype . "Continuous") (lts . 0.2) (lw . 40) (gw . 6.25) (ltgen . nil)) ("Eje" (color . 24) (ltype . "DASHDOT") (lts . 0.2) (lw . 40) (gw . 3.125) (ltgen . T)) ("Predios" (color . 64) (ltype . "Continuous") (lts . 1) (lw . -3) (gw . 2.5) (ltgen . nil)) ("Afectada" (color . 6) (ltype . "DASHDOT") (lts . 0.2) (lw . 40) (gw . 3.125) (ltgen . nil)) ("Achurado" (color . 71) (pattern . "SOLID") (ltype . "Continuous") (lts . 1) (lw . 50) (hscale . 1.25)) ("Matriz" (color . 5) (ltype . "Continuous") (lts . 1) (lw . 50) (gw . 4) (ltgen . nil)) ("Via" (color . 0) (ltype . "Continuous") (lts . 0.2) (lw . 40) (gw . 0) (ltgen . nil)) ("Rios" (color . 4) (ltype . "Continuous") (lts . 0.2) (lw . 40) (gw . 2.5) (ltgen . nil)))
  ("20000" ("Derecho" (color . 230) (ltype . "Continuous") (lts . 0.2) (lw . 40) (gw . 10) (ltgen . nil)) ("Eje" (color . 24) (ltype . "DASHDOT") (lts . 0.2) (lw . 40) (gw . 5) (ltgen . T)) ("Predios" (color . 64) (ltype . "Continuous") (lts . 1) (lw . -3) (gw . 4) (ltgen . nil)) ("Afectada" (color . 6) (ltype . "DASHDOT") (lts . 0.2) (lw . 40) (gw . 5) (ltgen . nil)) ("Achurado" (color . 71) (pattern . "SOLID") (ltype . "Continuous") (lts . 1) (lw . 50) (hscale . 2)) ("Matriz" (color . 5) (ltype . "Continuous") (lts . 1) (lw . 50) (gw . 6.4) (ltgen . nil)) ("Via" (color . 0) (ltype . "Continuous") (lts . 0.2) (lw . 40) (gw . 0) (ltgen . nil)) ("Rios" (color . 4) (ltype . "Continuous") (lts . 0.2) (lw . 40) (gw . 4) (ltgen . nil)))
  ("25000" ("Derecho" (color . 230) (ltype . "Continuous") (lts . 0.2) (lw . 40) (gw . 12.5) (ltgen . nil)) ("Eje" (color . 24) (ltype . "DASHDOT") (lts . 0.2) (lw . 40) (gw . 6.25) (ltgen . T)) ("Predios" (color . 64) (ltype . "Continuous") (lts . 1) (lw . -3) (gw . 5) (ltgen . nil)) ("Afectada" (color . 6) (ltype . "DASHDOT") (lts . 0.2) (lw . 40) (gw . 6.25) (ltgen . nil)) ("Achurado" (color . 71) (pattern . "SOLID") (ltype . "Continuous") (lts . 1) (lw . 50) (hscale . 2.5)) ("Matriz" (color . 5) (ltype . "Continuous") (lts . 1) (lw . 50) (gw . 8) (ltgen . nil)) ("Via" (color . 0) (ltype . "Continuous") (lts . 0.2) (lw . 40) (gw . 0) (ltgen . nil)) ("Rios" (color . 4) (ltype . "Continuous") (lts . 0.2) (lw . 40) (gw . 5) (ltgen . nil)))
))

(setq *UBI_STYLE_MAP_MATRIZ* '( ;; BR 2026-09-21: tabla literal ESCALAS.xlsx hoja MATRIZ (=UBICACION salvo Matriz GW=Derecho y LW Default).
  ("20" ("Derecho" (color . 230) (ltype . "Continuous") (lts . 0.2) (lw . 40) (gw . 0.01) (ltgen . nil)) ("Eje" (color . 24) (ltype . "DASHDOT") (lts . 0.2) (lw . 40) (gw . 0.005) (ltgen . T)) ("Predios" (color . 64) (ltype . "Continuous") (lts . 1) (lw . -3) (gw . 0.004) (ltgen . nil)) ("Afectada" (color . 1) (ltype . "DASHED2") (lts . 5) (lw . 50) (gw . 0.004) (ltgen . T)) ("Achurado" (color . 71) (pattern . "SOLID") (ltype . "Continuous") (lts . 1) (lw . 50) (hscale . 0.002)) ("Matriz" (color . 5) (ltype . "Continuous") (lts . 1) (lw . -3) (gw . 0.01) (ltgen . nil)) ("Via" (color . 0) (ltype . "Continuous") (lts . 0.2) (lw . 40) (gw . 0) (ltgen . nil)) ("Rios" (color . 4) (ltype . "Continuous") (lts . 0.2) (lw . 40) (gw . 0.004) (ltgen . nil)))
  ("25" ("Derecho" (color . 230) (ltype . "Continuous") (lts . 0.2) (lw . 40) (gw . 0.013) (ltgen . nil)) ("Eje" (color . 24) (ltype . "DASHDOT") (lts . 0.2) (lw . 40) (gw . 0.006) (ltgen . T)) ("Predios" (color . 64) (ltype . "Continuous") (lts . 1) (lw . -3) (gw . 0.005) (ltgen . nil)) ("Afectada" (color . 1) (ltype . "DASHED2") (lts . 5) (lw . 50) (gw . 0.005) (ltgen . T)) ("Achurado" (color . 71) (pattern . "SOLID") (ltype . "Continuous") (lts . 1) (lw . 50) (hscale . 0.003)) ("Matriz" (color . 5) (ltype . "Continuous") (lts . 1) (lw . -3) (gw . 0.013) (ltgen . nil)) ("Via" (color . 0) (ltype . "Continuous") (lts . 0.2) (lw . 40) (gw . 0) (ltgen . nil)) ("Rios" (color . 4) (ltype . "Continuous") (lts . 0.2) (lw . 40) (gw . 0.005) (ltgen . nil)))
  ("50" ("Derecho" (color . 230) (ltype . "Continuous") (lts . 0.2) (lw . 40) (gw . 0.025) (ltgen . nil)) ("Eje" (color . 24) (ltype . "DASHDOT") (lts . 0.2) (lw . 40) (gw . 0.013) (ltgen . T)) ("Predios" (color . 64) (ltype . "Continuous") (lts . 1) (lw . -3) (gw . 0.01) (ltgen . nil)) ("Afectada" (color . 1) (ltype . "DASHED2") (lts . 5) (lw . 50) (gw . 0.01) (ltgen . T)) ("Achurado" (color . 71) (pattern . "SOLID") (ltype . "Continuous") (lts . 1) (lw . 50) (hscale . 0.005)) ("Matriz" (color . 5) (ltype . "Continuous") (lts . 1) (lw . -3) (gw . 0.025) (ltgen . nil)) ("Via" (color . 0) (ltype . "Continuous") (lts . 0.2) (lw . 40) (gw . 0) (ltgen . nil)) ("Rios" (color . 4) (ltype . "Continuous") (lts . 0.2) (lw . 40) (gw . 0.01) (ltgen . nil)))
  ("75" ("Derecho" (color . 230) (ltype . "Continuous") (lts . 0.2) (lw . 40) (gw . 0.038) (ltgen . nil)) ("Eje" (color . 24) (ltype . "DASHDOT") (lts . 0.2) (lw . 40) (gw . 0.019) (ltgen . T)) ("Predios" (color . 64) (ltype . "Continuous") (lts . 1) (lw . -3) (gw . 0.015) (ltgen . nil)) ("Afectada" (color . 1) (ltype . "DASHED2") (lts . 5) (lw . 50) (gw . 0.015) (ltgen . T)) ("Achurado" (color . 71) (pattern . "SOLID") (ltype . "Continuous") (lts . 1) (lw . 50) (hscale . 0.008)) ("Matriz" (color . 5) (ltype . "Continuous") (lts . 1) (lw . -3) (gw . 0.038) (ltgen . nil)) ("Via" (color . 0) (ltype . "Continuous") (lts . 0.2) (lw . 40) (gw . 0) (ltgen . nil)) ("Rios" (color . 4) (ltype . "Continuous") (lts . 0.2) (lw . 40) (gw . 0.015) (ltgen . nil)))
  ("100" ("Derecho" (color . 230) (ltype . "Continuous") (lts . 0.2) (lw . 40) (gw . 0.05) (ltgen . nil)) ("Eje" (color . 24) (ltype . "DASHDOT") (lts . 0.2) (lw . 40) (gw . 0.025) (ltgen . T)) ("Predios" (color . 64) (ltype . "Continuous") (lts . 1) (lw . -3) (gw . 0.02) (ltgen . nil)) ("Afectada" (color . 1) (ltype . "DASHED2") (lts . 5) (lw . 50) (gw . 0.02) (ltgen . T)) ("Achurado" (color . 71) (pattern . "SOLID") (ltype . "Continuous") (lts . 1) (lw . 50) (hscale . 0.01)) ("Matriz" (color . 5) (ltype . "Continuous") (lts . 1) (lw . -3) (gw . 0.05) (ltgen . nil)) ("Via" (color . 0) (ltype . "Continuous") (lts . 0.2) (lw . 40) (gw . 0) (ltgen . nil)) ("Rios" (color . 4) (ltype . "Continuous") (lts . 0.2) (lw . 40) (gw . 0.02) (ltgen . nil)))
  ("125" ("Derecho" (color . 230) (ltype . "Continuous") (lts . 0.2) (lw . 40) (gw . 0.063) (ltgen . nil)) ("Eje" (color . 24) (ltype . "DASHDOT") (lts . 0.2) (lw . 40) (gw . 0.031) (ltgen . T)) ("Predios" (color . 64) (ltype . "Continuous") (lts . 1) (lw . -3) (gw . 0.025) (ltgen . nil)) ("Afectada" (color . 1) (ltype . "DASHED2") (lts . 5) (lw . 50) (gw . 0.025) (ltgen . T)) ("Achurado" (color . 71) (pattern . "SOLID") (ltype . "Continuous") (lts . 1) (lw . 50) (hscale . 0.013)) ("Matriz" (color . 5) (ltype . "Continuous") (lts . 1) (lw . -3) (gw . 0.063) (ltgen . nil)) ("Via" (color . 0) (ltype . "Continuous") (lts . 0.2) (lw . 40) (gw . 0) (ltgen . nil)) ("Rios" (color . 4) (ltype . "Continuous") (lts . 0.2) (lw . 40) (gw . 0.025) (ltgen . nil)))
  ("200" ("Derecho" (color . 230) (ltype . "Continuous") (lts . 0.2) (lw . 40) (gw . 0.1) (ltgen . nil)) ("Eje" (color . 24) (ltype . "DASHDOT") (lts . 0.2) (lw . 40) (gw . 0.05) (ltgen . T)) ("Predios" (color . 64) (ltype . "Continuous") (lts . 1) (lw . -3) (gw . 0.04) (ltgen . nil)) ("Afectada" (color . 1) (ltype . "DASHED2") (lts . 5) (lw . 50) (gw . 0.04) (ltgen . T)) ("Achurado" (color . 71) (pattern . "SOLID") (ltype . "Continuous") (lts . 1) (lw . 50) (hscale . 0.02)) ("Matriz" (color . 5) (ltype . "Continuous") (lts . 1) (lw . -3) (gw . 0.1) (ltgen . nil)) ("Via" (color . 0) (ltype . "Continuous") (lts . 0.2) (lw . 40) (gw . 0) (ltgen . nil)) ("Rios" (color . 4) (ltype . "Continuous") (lts . 0.2) (lw . 40) (gw . 0.04) (ltgen . nil)))
  ("250" ("Derecho" (color . 230) (ltype . "Continuous") (lts . 0.2) (lw . 40) (gw . 0.125) (ltgen . nil)) ("Eje" (color . 24) (ltype . "DASHDOT") (lts . 0.2) (lw . 40) (gw . 0.063) (ltgen . T)) ("Predios" (color . 64) (ltype . "Continuous") (lts . 1) (lw . -3) (gw . 0.05) (ltgen . nil)) ("Afectada" (color . 1) (ltype . "DASHED2") (lts . 5) (lw . 50) (gw . 0.05) (ltgen . T)) ("Achurado" (color . 71) (pattern . "SOLID") (ltype . "Continuous") (lts . 1) (lw . 50) (hscale . 0.025)) ("Matriz" (color . 5) (ltype . "Continuous") (lts . 1) (lw . -3) (gw . 0.125) (ltgen . nil)) ("Via" (color . 0) (ltype . "Continuous") (lts . 0.2) (lw . 40) (gw . 0) (ltgen . nil)) ("Rios" (color . 4) (ltype . "Continuous") (lts . 0.2) (lw . 40) (gw . 0.05) (ltgen . nil)))
  ("500" ("Derecho" (color . 230) (ltype . "Continuous") (lts . 0.2) (lw . 40) (gw . 0.25) (ltgen . nil)) ("Eje" (color . 24) (ltype . "DASHDOT") (lts . 0.2) (lw . 40) (gw . 0.125) (ltgen . T)) ("Predios" (color . 64) (ltype . "Continuous") (lts . 1) (lw . -3) (gw . 0.1) (ltgen . nil)) ("Afectada" (color . 1) (ltype . "DASHED2") (lts . 5) (lw . 50) (gw . 0.1) (ltgen . T)) ("Achurado" (color . 71) (pattern . "SOLID") (ltype . "Continuous") (lts . 1) (lw . 50) (hscale . 0.05)) ("Matriz" (color . 5) (ltype . "Continuous") (lts . 1) (lw . -3) (gw . 0.25) (ltgen . nil)) ("Via" (color . 0) (ltype . "Continuous") (lts . 0.2) (lw . 40) (gw . 0) (ltgen . nil)) ("Rios" (color . 4) (ltype . "Continuous") (lts . 0.2) (lw . 40) (gw . 0.1) (ltgen . nil)))
  ("750" ("Derecho" (color . 230) (ltype . "Continuous") (lts . 0.2) (lw . 40) (gw . 0.375) (ltgen . nil)) ("Eje" (color . 24) (ltype . "DASHDOT") (lts . 0.2) (lw . 40) (gw . 0.188) (ltgen . T)) ("Predios" (color . 64) (ltype . "Continuous") (lts . 1) (lw . -3) (gw . 0.15) (ltgen . nil)) ("Afectada" (color . 1) (ltype . "DASHED2") (lts . 5) (lw . 50) (gw . 0.15) (ltgen . T)) ("Achurado" (color . 71) (pattern . "SOLID") (ltype . "Continuous") (lts . 1) (lw . 50) (hscale . 0.075)) ("Matriz" (color . 5) (ltype . "Continuous") (lts . 1) (lw . -3) (gw . 0.375) (ltgen . nil)) ("Via" (color . 0) (ltype . "Continuous") (lts . 0.2) (lw . 40) (gw . 0) (ltgen . nil)) ("Rios" (color . 4) (ltype . "Continuous") (lts . 0.2) (lw . 40) (gw . 0.15) (ltgen . nil)))
  ("1000" ("Derecho" (color . 230) (ltype . "Continuous") (lts . 0.2) (lw . 40) (gw . 0.5) (ltgen . nil)) ("Eje" (color . 24) (ltype . "DASHDOT") (lts . 0.2) (lw . 40) (gw . 0.25) (ltgen . T)) ("Predios" (color . 64) (ltype . "Continuous") (lts . 1) (lw . -3) (gw . 0.2) (ltgen . nil)) ("Afectada" (color . 1) (ltype . "DASHED2") (lts . 5) (lw . 50) (gw . 0.2) (ltgen . T)) ("Achurado" (color . 71) (pattern . "SOLID") (ltype . "Continuous") (lts . 1) (lw . 50) (hscale . 0.1)) ("Matriz" (color . 5) (ltype . "Continuous") (lts . 1) (lw . -3) (gw . 0.5) (ltgen . nil)) ("Via" (color . 0) (ltype . "Continuous") (lts . 0.2) (lw . 40) (gw . 0) (ltgen . nil)) ("Rios" (color . 4) (ltype . "Continuous") (lts . 0.2) (lw . 40) (gw . 0.2) (ltgen . nil)))
  ("1250" ("Derecho" (color . 230) (ltype . "Continuous") (lts . 0.2) (lw . 40) (gw . 0.625) (ltgen . nil)) ("Eje" (color . 24) (ltype . "DASHDOT") (lts . 0.2) (lw . 40) (gw . 0.313) (ltgen . T)) ("Predios" (color . 64) (ltype . "Continuous") (lts . 1) (lw . -3) (gw . 0.25) (ltgen . nil)) ("Afectada" (color . 1) (ltype . "DASHED2") (lts . 5) (lw . 50) (gw . 0.25) (ltgen . T)) ("Achurado" (color . 71) (pattern . "SOLID") (ltype . "Continuous") (lts . 1) (lw . 50) (hscale . 0.125)) ("Matriz" (color . 5) (ltype . "Continuous") (lts . 1) (lw . -3) (gw . 0.625) (ltgen . nil)) ("Via" (color . 0) (ltype . "Continuous") (lts . 0.2) (lw . 40) (gw . 0) (ltgen . nil)) ("Rios" (color . 4) (ltype . "Continuous") (lts . 0.2) (lw . 40) (gw . 0.25) (ltgen . nil)))
  ("2000" ("Derecho" (color . 230) (ltype . "Continuous") (lts . 0.2) (lw . 40) (gw . 1) (ltgen . nil)) ("Eje" (color . 24) (ltype . "DASHDOT") (lts . 0.2) (lw . 40) (gw . 0.5) (ltgen . T)) ("Predios" (color . 64) (ltype . "Continuous") (lts . 1) (lw . -3) (gw . 0.4) (ltgen . nil)) ("Afectada" (color . 1) (ltype . "DASHED2") (lts . 5) (lw . 50) (gw . 0.4) (ltgen . T)) ("Achurado" (color . 71) (pattern . "SOLID") (ltype . "Continuous") (lts . 1) (lw . 50) (hscale . 0.2)) ("Matriz" (color . 5) (ltype . "Continuous") (lts . 1) (lw . -3) (gw . 1) (ltgen . nil)) ("Via" (color . 0) (ltype . "Continuous") (lts . 0.2) (lw . 40) (gw . 0) (ltgen . nil)) ("Rios" (color . 4) (ltype . "Continuous") (lts . 0.2) (lw . 40) (gw . 0.4) (ltgen . nil)))
  ("2500" ("Derecho" (color . 230) (ltype . "Continuous") (lts . 0.2) (lw . 40) (gw . 1.25) (ltgen . nil)) ("Eje" (color . 24) (ltype . "DASHDOT") (lts . 0.2) (lw . 40) (gw . 0.625) (ltgen . T)) ("Predios" (color . 64) (ltype . "Continuous") (lts . 1) (lw . -3) (gw . 0.5) (ltgen . nil)) ("Afectada" (color . 1) (ltype . "DASHED2") (lts . 5) (lw . 50) (gw . 0.5) (ltgen . T)) ("Achurado" (color . 71) (pattern . "SOLID") (ltype . "Continuous") (lts . 1) (lw . 50) (hscale . 0.25)) ("Matriz" (color . 5) (ltype . "Continuous") (lts . 1) (lw . -3) (gw . 1.25) (ltgen . nil)) ("Via" (color . 0) (ltype . "Continuous") (lts . 0.2) (lw . 40) (gw . 0) (ltgen . nil)) ("Rios" (color . 4) (ltype . "Continuous") (lts . 0.2) (lw . 40) (gw . 0.5) (ltgen . nil)))
  ("5000" ("Derecho" (color . 230) (ltype . "Continuous") (lts . 0.2) (lw . 40) (gw . 2.5) (ltgen . nil)) ("Eje" (color . 24) (ltype . "DASHDOT") (lts . 0.2) (lw . 40) (gw . 1.25) (ltgen . T)) ("Predios" (color . 64) (ltype . "Continuous") (lts . 1) (lw . -3) (gw . 1) (ltgen . nil)) ("Afectada" (color . 1) (ltype . "DASHED2") (lts . 5) (lw . 50) (gw . 1) (ltgen . T)) ("Achurado" (color . 71) (pattern . "SOLID") (ltype . "Continuous") (lts . 1) (lw . 50) (hscale . 0.5)) ("Matriz" (color . 5) (ltype . "Continuous") (lts . 1) (lw . -3) (gw . 2.5) (ltgen . nil)) ("Via" (color . 0) (ltype . "Continuous") (lts . 0.2) (lw . 40) (gw . 0) (ltgen . nil)) ("Rios" (color . 4) (ltype . "Continuous") (lts . 0.2) (lw . 40) (gw . 1) (ltgen . nil)))
  ("7500" ("Derecho" (color . 230) (ltype . "Continuous") (lts . 0.2) (lw . 40) (gw . 3.75) (ltgen . nil)) ("Eje" (color . 24) (ltype . "DASHDOT") (lts . 0.2) (lw . 40) (gw . 1.875) (ltgen . T)) ("Predios" (color . 64) (ltype . "Continuous") (lts . 1) (lw . -3) (gw . 1.5) (ltgen . nil)) ("Afectada" (color . 1) (ltype . "DASHED2") (lts . 5) (lw . 50) (gw . 1.5) (ltgen . T)) ("Achurado" (color . 71) (pattern . "SOLID") (ltype . "Continuous") (lts . 1) (lw . 50) (hscale . 0.75)) ("Matriz" (color . 5) (ltype . "Continuous") (lts . 1) (lw . -3) (gw . 3.75) (ltgen . nil)) ("Via" (color . 0) (ltype . "Continuous") (lts . 0.2) (lw . 40) (gw . 0) (ltgen . nil)) ("Rios" (color . 4) (ltype . "Continuous") (lts . 0.2) (lw . 40) (gw . 1.5) (ltgen . nil)))
  ("10000" ("Derecho" (color . 230) (ltype . "Continuous") (lts . 0.2) (lw . 40) (gw . 5) (ltgen . nil)) ("Eje" (color . 24) (ltype . "DASHDOT") (lts . 0.2) (lw . 40) (gw . 2.5) (ltgen . T)) ("Predios" (color . 64) (ltype . "Continuous") (lts . 1) (lw . -3) (gw . 2) (ltgen . nil)) ("Afectada" (color . 1) (ltype . "DASHED2") (lts . 5) (lw . 50) (gw . 2) (ltgen . T)) ("Achurado" (color . 71) (pattern . "SOLID") (ltype . "Continuous") (lts . 1) (lw . 50) (hscale . 1)) ("Matriz" (color . 5) (ltype . "Continuous") (lts . 1) (lw . -3) (gw . 5) (ltgen . nil)) ("Via" (color . 0) (ltype . "Continuous") (lts . 0.2) (lw . 40) (gw . 0) (ltgen . nil)) ("Rios" (color . 4) (ltype . "Continuous") (lts . 0.2) (lw . 40) (gw . 2) (ltgen . nil)))
  ("12500" ("Derecho" (color . 230) (ltype . "Continuous") (lts . 0.2) (lw . 40) (gw . 6.25) (ltgen . nil)) ("Eje" (color . 24) (ltype . "DASHDOT") (lts . 0.2) (lw . 40) (gw . 3.125) (ltgen . T)) ("Predios" (color . 64) (ltype . "Continuous") (lts . 1) (lw . -3) (gw . 2.5) (ltgen . nil)) ("Afectada" (color . 1) (ltype . "DASHED2") (lts . 5) (lw . 50) (gw . 2.5) (ltgen . T)) ("Achurado" (color . 71) (pattern . "SOLID") (ltype . "Continuous") (lts . 1) (lw . 50) (hscale . 1.25)) ("Matriz" (color . 5) (ltype . "Continuous") (lts . 1) (lw . -3) (gw . 6.25) (ltgen . nil)) ("Via" (color . 0) (ltype . "Continuous") (lts . 0.2) (lw . 40) (gw . 0) (ltgen . nil)) ("Rios" (color . 4) (ltype . "Continuous") (lts . 0.2) (lw . 40) (gw . 2.5) (ltgen . nil)))
  ("20000" ("Derecho" (color . 230) (ltype . "Continuous") (lts . 0.2) (lw . 40) (gw . 10) (ltgen . nil)) ("Eje" (color . 24) (ltype . "DASHDOT") (lts . 0.2) (lw . 40) (gw . 5) (ltgen . T)) ("Predios" (color . 64) (ltype . "Continuous") (lts . 1) (lw . -3) (gw . 4) (ltgen . nil)) ("Afectada" (color . 1) (ltype . "DASHED2") (lts . 5) (lw . 50) (gw . 4) (ltgen . T)) ("Achurado" (color . 71) (pattern . "SOLID") (ltype . "Continuous") (lts . 1) (lw . 50) (hscale . 2)) ("Matriz" (color . 5) (ltype . "Continuous") (lts . 1) (lw . -3) (gw . 10) (ltgen . nil)) ("Via" (color . 0) (ltype . "Continuous") (lts . 0.2) (lw . 40) (gw . 0) (ltgen . nil)) ("Rios" (color . 4) (ltype . "Continuous") (lts . 0.2) (lw . 40) (gw . 4) (ltgen . nil)))
  ("25000" ("Derecho" (color . 230) (ltype . "Continuous") (lts . 0.2) (lw . 40) (gw . 12.5) (ltgen . nil)) ("Eje" (color . 24) (ltype . "DASHDOT") (lts . 0.2) (lw . 40) (gw . 6.25) (ltgen . T)) ("Predios" (color . 64) (ltype . "Continuous") (lts . 1) (lw . -3) (gw . 5) (ltgen . nil)) ("Afectada" (color . 1) (ltype . "DASHED2") (lts . 5) (lw . 50) (gw . 5) (ltgen . T)) ("Achurado" (color . 71) (pattern . "SOLID") (ltype . "Continuous") (lts . 1) (lw . 50) (hscale . 2.5)) ("Matriz" (color . 5) (ltype . "Continuous") (lts . 1) (lw . -3) (gw . 12.5) (ltgen . nil)) ("Via" (color . 0) (ltype . "Continuous") (lts . 0.2) (lw . 40) (gw . 0) (ltgen . nil)) ("Rios" (color . 4) (ltype . "Continuous") (lts . 0.2) (lw . 40) (gw . 5) (ltgen . nil)))
))

(defun UBI_GetUbicacionStyle_BR (scl_str elem / scl_entry tipo mapa)
  ;; BR: selector por *GM_PLANO_TIPO* con fallback UBICACION -> 1000.
  (setq tipo (if (and (boundp (quote *GM_PLANO_TIPO*)) *GM_PLANO_TIPO*) *GM_PLANO_TIPO* "UBICACION"))
  (setq mapa (cond ((= tipo "DIAGNOSTICO") *UBI_STYLE_MAP_DIAGNOSTICO*) ((= tipo "PERIMETRICO") *UBI_STYLE_MAP_PERIMETRICO*) ((= tipo "MATRIZ") *UBI_STYLE_MAP_MATRIZ*) (t *UBI_STYLE_MAP*)))
  (setq scl_entry (cdr (assoc scl_str mapa)))
  (if (not scl_entry) (setq scl_entry (cdr (assoc scl_str *UBI_STYLE_MAP*))))
  (if (not scl_entry) (setq scl_entry (cdr (assoc "1000" mapa))))
  (if (not scl_entry) (setq scl_entry (cdr (assoc "1000" *UBI_STYLE_MAP*))))
  (if scl_entry (assoc elem scl_entry))
)

(defun UBI_GetUbicacionStyle (scl_str elem / scl_entry)
  ;; POR QUE delega en BR: el lote debe formatear segun *GM_PLANO_TIPO*
  ;; (UBICACION/DIAGNOSTICO/PERIMETRICO/MATRIZ). Con UBICACION el mapa es el
  ;; mismo de antes, asi que el comportamiento por defecto no cambia.
  (UBI_GetUbicacionStyle_BR scl_str elem)
)

(defun UBI_GetUbicacionStyleVal (style_entry key default / pair)
  (if (and style_entry (setq pair (assoc key (cdr style_entry)))) (cdr pair) default)
)

;; ==============================================================================
;; FUNCIONES AUXILIARES DEFENSIVAS Y DE B\\U+00DASQUEDA
;; ==============================================================================

(defun UBI_GetCodePrefix (str / pos)
  (setq pos (vl-string-position 45 str nil t)) ; Busca el \\U+00FAltimo "-"
  (if pos (substr str 1 pos) str)
)

;; PA-4 (H10) 2026-09-28: str-starts-with se define en LAYOUT_UBICACION.lsp
;; (copia canonica, cargada despues de este archivo y usada por AUTOMATIZACION).
;; Aqui vivia una tercera copia muerta, sin llamadas en este modulo.

(defun UBI_GetHyperlinkString (obj / hlinks cnt i hl match url desc t_hl)
  (setq match nil t_hl (getvar "MILLISECS"))
  (if (not (vl-catch-all-error-p (setq hlinks (vl-catch-all-apply 'vla-get-Hyperlinks (list obj)))))
    (progn
      ;; AUD1: Count e Item con catch (una entidad que muere a mitad del
      ;; escaneo ya no aborta el lote con hlinks vivo).
      (setq cnt (vl-catch-all-apply 'vla-get-Count (list hlinks)) i 0)
      (if (or (vl-catch-all-error-p cnt) (not (numberp cnt))) (setq cnt 0))
      (while (and (< i cnt) (not match))
        (setq hl (vl-catch-all-apply 'vla-Item (list hlinks i)))
        (if (vl-catch-all-error-p hl) (setq hl nil))
        (setq url (if hl (vl-catch-all-apply 'vla-get-URL (list hl)) nil))
        (if (or (vl-catch-all-error-p url) (not url) (= url "#")) (setq url ""))
        (setq desc (vl-catch-all-apply 'vla-get-URLDescription (list hl)))
        (if (or (vl-catch-all-error-p desc) (not desc) (= desc "#")) (setq desc ""))
        (setq url (vl-string-trim " \t\n\r" url) desc (vl-string-trim " \t\n\r" desc))
        (if (/= desc "") (setq match desc) (if (/= url "") (setq match url)))
        ;; OPT1/BZ-OPT1: liberar hl local (el wrapper de obj lo libera su llamador).
        (if (and hl (not (vl-catch-all-error-p hl)))
          (vl-catch-all-apply 'vlax-release-object (list hl))
        )
        (setq hl nil i (1+ i))
      )
      (if (and hlinks (not (vl-catch-all-error-p hlinks)))
        (vl-catch-all-apply 'vlax-release-object (list hlinks))
      )
      (setq hlinks nil)
    )
  )
  ;; OPT5 2026-09-27 (F0): acumulador de costo real de lectura de hipervinculos
  ;; (lo publica UBI_ApplyAutoFormat como tramo HL_MS/HL_N del FORMATO).
  (if (numberp t_hl)
    (progn
      (setq *GM_FMT_HL_MS* (+ *GM_FMT_HL_MS* (max 0 (- (getvar "MILLISECS") t_hl))))
      (setq *GM_FMT_HL_N* (1+ *GM_FMT_HL_N*))))
  match
)

(defun UBI_FindPolygonByCode (target_code / ss i obj vobj hl_str match_ent code_up)
  ;; El codigo chapas el terrenito del mapa :v .
  ;; OPT1: vobj se libera por iteracion para no acumular wrappers en el lote.
  ;; OPT6 (F2): con indice de lote la busqueda es en memoria; sin indice, barrido COM.
  (setq match_ent nil code_up (if (= (type target_code) 'STR) (vl-string-trim " \t\n\r" (strcase target_code)) ""))
  (if (/= code_up "")
    (if (and *UBI_ENT_INDEX_READY* *UBI_POLY_INDEX*)
      (setq match_ent (UBI_IndexFindPolyByCode code_up))
      (progn
      (setq ss (ssget "X" (list (cons 0 "LWPOLYLINE,POLYLINE") (cons 410 "Model"))))
      (if ss
        (progn
          (setq i 0)
          (while (and (< i (sslength ss)) (not match_ent))
            (setq obj (ssname ss i))
            ;; AUD1: creacion con catch; entidad caida = se salta.
            (setq vobj (vl-catch-all-apply 'vlax-ename->vla-object (list obj)))
            (if (vl-catch-all-error-p vobj) (setq vobj nil))
            (setq hl_str (if vobj (UBI_GetHyperlinkString vobj) nil))
            (if (and vobj (not (vl-catch-all-error-p vobj)))
              (vl-catch-all-apply 'vlax-release-object (list vobj))
            )
            (setq vobj nil)
            (if (and hl_str (= (vl-string-trim " \t\n\r" (strcase hl_str)) code_up))
              (setq match_ent obj)
            )
            (setq i (1+ i))
          )
          (setq ss nil) (gc)
        )
      )
      )
    )
  )
  match_ent
)

;; Nombre historico conservado para llamadas existentes dentro de la suite.
(defun UBI_FindPolyByCode (target_code)
  (UBI_FindPolygonByCode target_code)
)

(defun UBI_NormalizeSearchKey (value / result)
  (setq result (if (= (type value) 'STR) (strcase (vl-string-trim " \t\n\r" value)) ""))
  (while (vl-string-search " " result) (setq result (vl-string-subst "" " " result)))
  (while (vl-string-search "." result) (setq result (vl-string-subst "" "." result)))
  (while (vl-string-search "-" result) (setq result (vl-string-subst "" "-" result)))
  result
)

(defun UBI_PointInsideBox (point minpt maxpt)
  (and point minpt maxpt
       (>= (car point) (car minpt)) (<= (car point) (car maxpt))
       (>= (cadr point) (cadr minpt)) (<= (cadr point) (cadr maxpt)))
)

(defun UBI_FindPolygonByReference (reference / target ss_text ss_poly i j txt_ent txt_obj txt_value ins minpt maxpt poly_obj raw pts result)
  ;; Fallback para plantillas donde el hipervinculo usa U.C. y no el codigo CSV.
  ;; UCF1 2026-10-24: el fallback solo tiene sentido para una U.C. real, y una
  ;; U.C. siempre lleva digitos (formato "U.C. 09091"). Si la referencia no
  ;; tiene ninguno (ej. "t", campo U.C. podrido del CSV en la corrida Chagual
  ;; del 21-10), se devuelve nil: antes el barrido de textos elegia el primero
  ;; que contuviera la letra y MODELO abortaba con
  ;; "bad argument type: safearrayp #<variant 8197 ...>".
  (setq target (UBI_NormalizeSearchKey reference) result nil)
  (if (and (/= target "") (wcmatch target "*#*"))
    (progn
      (setq ss_text (ssget "X" (list (cons 0 "TEXT,MTEXT") (cons 410 "Model")))
            ss_poly (ssget "X" (list (cons 0 "LWPOLYLINE,POLYLINE") (cons 410 "Model"))))
      ;; Algunas plantillas guardan la U.C. como hipervinculo del poligono.
      ;; OPT6 (F2): con indice de lote la busqueda es en memoria; sin indice,
      ;; se conserva el barrido COM original.
      (if (and *UBI_ENT_INDEX_READY* *UBI_POLY_INDEX*)
        (setq result (UBI_IndexFindPolyByRef target))
        (progn
      (if ss_poly
        (progn
          (setq j 0)
          (while (and (< j (sslength ss_poly)) (not result))
            ;; AUD1: creacion con catch; entidad caida = se salta.
            (setq poly_obj (vl-catch-all-apply 'vlax-ename->vla-object (list (ssname ss_poly j))))
            (if (vl-catch-all-error-p poly_obj) (setq poly_obj nil))
            (if (and poly_obj (= target (UBI_NormalizeSearchKey (UBI_GetHyperlinkString poly_obj))))
              (setq result (ssname ss_poly j))
            )
            ;; OPT1/BZ-OPT1: liberar wrapper por iteracion (lote largo).
            (if (and poly_obj (not (vl-catch-all-error-p poly_obj)))
              (vl-catch-all-apply 'vlax-release-object (list poly_obj))
            )
            (setq poly_obj nil j (1+ j))
          )
        )
      )
        )
      )
      (if (and (not result) ss_text ss_poly)
        (progn
          (setq i 0)
          (while (and (< i (sslength ss_text)) (not result))
            (setq txt_ent (ssname ss_text i))
            ;; AUD1: creacion con catch (txt y poly); entidad caida = se salta.
            (setq txt_obj (vl-catch-all-apply 'vlax-ename->vla-object (list txt_ent)))
            (if (vl-catch-all-error-p txt_obj) (setq txt_obj nil))
            (setq txt_value (if txt_obj (vl-catch-all-apply 'vla-get-TextString (list txt_obj)) nil))
            (if (and (not (vl-catch-all-error-p txt_value)) txt_value
                     (vl-string-search target (UBI_NormalizeSearchKey txt_value)))
              (progn
                ;; UCF1 2026-10-24: InsertionPoint llega como VARIANT (ej.
                ;; #<variant 8197>), no como SAFEARRAY: sin desenvolverlo,
                ;; vlax-safearray->list aborta con "bad argument type:
                ;; safearrayp". Se desenvuelve con vlax-variant-value dentro
                ;; de catch-all; si la propiedad ya viniera como SAFEARRAY,
                ;; ese paso falla y se conserva el original. La lista solo se
                ;; usa si trae coordenadas X/Y numericas.
                (setq raw (vl-catch-all-apply 'vlax-get-property (list txt_obj 'InsertionPoint)))
                (if (not (vl-catch-all-error-p raw))
                  (progn
                    (setq pts (vl-catch-all-apply 'vlax-variant-value (list raw)))
                    (if (vl-catch-all-error-p pts) (setq pts raw))
                    (setq pts (vl-catch-all-apply 'vlax-safearray->list (list pts)))
                    (if (and (not (vl-catch-all-error-p pts)) (listp pts)
                             (numberp (car pts)) (numberp (cadr pts)))
                      (progn
                        (setq ins pts j 0)
                        (while (and (< j (sslength ss_poly)) (not result))
                          (setq poly_obj (vl-catch-all-apply 'vlax-ename->vla-object (list (ssname ss_poly j))))
                          (if (vl-catch-all-error-p poly_obj) (setq poly_obj nil))
                          (if (not (vl-catch-all-error-p (vl-catch-all-apply 'vla-getboundingbox (list poly_obj 'minpt 'maxpt))))
                            (progn
                              (setq minpt (vlax-safearray->list minpt) maxpt (vlax-safearray->list maxpt))
                              (if (UBI_PointInsideBox ins minpt maxpt) (setq result (ssname ss_poly j)))
                            )
                          )
                          ;; OPT1/BZ-OPT1: liberar wrapper de bbox por iteracion.
                          (if (and poly_obj (not (vl-catch-all-error-p poly_obj)))
                            (vl-catch-all-apply 'vlax-release-object (list poly_obj))
                          )
                          (setq poly_obj nil j (1+ j))
                        )
                      )
                    )
                  )
                )
              )
            )
            ;; OPT1/BZ-OPT1: liberar wrapper de texto por iteracion.
            (if (and txt_obj (not (vl-catch-all-error-p txt_obj)))
              (vl-catch-all-apply 'vlax-release-object (list txt_obj))
            )
            (setq txt_obj nil i (1+ i))
          )
        )
      )
    )
  )
  (setq ss_text nil ss_poly nil txt_obj nil poly_obj nil)
  (gc)
  result
)

(defun UBI_FindPolygonByCodeOrReference (target_code reference / result)
  (setq result (UBI_FindPolygonByCode target_code))
  (if (not result) (setq result (UBI_FindPolygonByReference reference)))
  result
)

;; CHUNK 2026-09-29: el wrapper anonimo de vla-getboundingbox fugaba 3/vcodigo
;; (center/suggest/autoescala). Ahora se crea con catch, se libera siempre y la
;; lectura fallida deja el fallback documentado de cada funcion.
(defun UBI_GetPolygonCenter (poly_ent / minpt maxpt result vla_p)
  (if (and poly_ent (entget poly_ent))
    (progn
      (setq vla_p (vl-catch-all-apply 'vlax-ename->vla-object (list poly_ent)))
      (if (vl-catch-all-error-p vla_p)
        (setq vla_p nil))
      (if vla_p
        (progn
          (setq result (vl-catch-all-apply 'vla-getboundingbox (list vla_p 'minpt 'maxpt)))
          (GM:ReleaseObjectSafe vla_p)
          (if (not (vl-catch-all-error-p result))
            (progn
              (setq minpt (vlax-safearray->list minpt) maxpt (vlax-safearray->list maxpt))
              (list (/ (+ (car minpt) (car maxpt)) 2.0)
                    (/ (+ (cadr minpt) (cadr maxpt)) 2.0)
                    0.0)
            )
          )
        )
      )
    )
  )
)
